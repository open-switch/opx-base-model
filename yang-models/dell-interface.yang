module dell-interface {
  namespace "http://www.dellemc.com/networking/os10/dell-interface";
  prefix "dell-if";

  import ietf-interfaces { prefix "if"; }
  import dell-base-common { prefix "base-cmn"; }
  import dell-base-interface-common { prefix "base-if"; }
  import ietf-yang-types { prefix yang; }
  import iana-if-type { prefix "ianaift"; }
  import ietf-network-instance { prefix "ni"; }
  import dell-yang-types { prefix dell-yang; }
  organization "Dell EMC";
  contact "http://www.dell.com/support";

  description "This model augments the standard interface and adds Dell EMC specific
    extensions. This model contains the entry point for the interface
    object extensions.";

  revision "2019-01-21" {
    description "This revision fixes warnings.";
    reference "Network Platform Abstraction";
  }

  revision "2018-12-03" {
    description "This revision adds interface bandwidth utilization statistics.";
    reference "Network Platform Abstraction";
  }

  revision "2018-11-26" {
    description "Add ALL-VNI for clear counters RPC ";
    reference "Network Platform Abstraction";
  }

  revision 2018-10-23 {
    description "This revision adds the support for resilient hashing enable/disable for LAG globals.";
    reference
        "Network Platform Abstraction";
  }

  revision "2018-09-18" {
    description "Add default-vlan leaf to vlan-globals ";
    reference "Network Platform Abstraction";
  }

  revision "2018-08-27" {
    description "This revision corrects the type for untagged VLAN id for virtual network member interface";
    reference "Network Platform Abstraction";
  }

  revision "2018-08-17" {
    description "Fixing pyang IETF errors and adding documentation to the model.";
    reference "Network Platform Abstraction";
  }

  revision "2018-08-06" {
    description "This revision adds untagged VLAN id for virtual netowrk member interface";
    reference "Network Platform Abstraction";
  }

  revision "2018-06-27" {
    description "This revision adds ingress and egress split horizon attribute id";
    reference "Network Platform Abstraction";
  }

  revision "2018-05-31" {
    description "This revision adds error-message for LAG mode constrain";
    reference "Network Platform Abstraction";
  }

  revision "2018-05-07" {
    description "This revision adds ethernet ip/ipv6 interface statistics";
    reference "Network Platform Abstraction";
  }

  revision "2018-04-26" {
    description "This revision marks the vlan-globals container as presence container";
    reference "Network Platform Abstraction";
  }

  revision "2018-04-19" {
    description "Add leaf configured-fec in if/interface-state/interface. More details
                 in the leaf description";
    reference "Network Platform Abstraction";
  }

  revision "2018-04-02" {
    description "This revision adds ethernet interface statistics ";
    reference "Network Platform Abstraction";
  }

  revision "2018-03-29" {
    description "Add parent bridge attribute as part of the VLAN interface.";
    reference "Network Platform Abstraction";
  }

  revision "2018-02-26" {
    description "Modifying L3VLAN to L3IPVLAN in accordance with iana-if-type";
    reference "Network Platform Abstraction";
  }

  revision "2018-02-08" {
    description "Added statistics to track port headroom buffer occupancy.";
    reference "Network Platform Abstraction";
  }

  revision "2018-02-06" {
    description "Added max-speed leaf to interface state object";
    reference "Network Platform Abstraction";
  }

  revision "2018-01-22" {
    description "Added scaled-VLAN attribute to enable scaled VLAN deployment. Also
                 added VLAN-mode attribute to support L3 VLANs in scaled VLAN mode";
    reference "Network Platform Abstraction";
  }

  revision "2017-12-12" {
    description "Added ip-mtu leaf to interface state object";
    reference "Network Platform Abstraction";
  }

  revision "2017-11-20" {
    description "Moving must statement on the default-VLAN-id leaf to platform specific yang annotation.";
    reference "Network Platform Abstraction";
  }

  revision "2017-10-24" {
    description "Add ecn-marked packet counter";
    reference "Network Platform Abstraction";
  }

  revision "2017-10-23" {
    description "Change VLAN member tagged/untagged leaf constrains.";
    reference "Network Platform Abstraction";
  }

  revision "2017-10-10" {
    description "Add vlanSubInterface and VXLAN interface attributes";
    reference "Network Platform Abstraction";
  }

  revision 2017-10-09 {
        description
            "Add LAG-mode attribute to interface state LAG object.";
        reference "Network Platform Abstraction";
  }

  revision 2017-10-04 {
        description
            "Add MAC learn mode attribute to interface object.";
        reference "Network Platform Abstraction";
  }

  revision "2017-09-27" {
    description "Add per interface supported auto-negotiation attribute.";
    reference "Network Platform Abstraction";
  }

  revision "2016-01-01" {
    description "Initial version.";
    reference "Network Platform Abstraction";
  }

  augment "/if:interfaces" {
    container vlan-globals {
      presence "Enable default VLAN configurations";

      leaf default-vlan-id {
        type if:interface-ref;
        default "vlan1";
        description
              "Default VLAN id for the switch";
      }

      leaf default-vlan {
          type base-cmn:vlan-id;
          description "Default VLAN ID for the switch.
                       Differs from leaf default-vlan-id by type.";
      }

      leaf scaled-vlan{
            type boolean;
            default false;
            description
                "To enable scaled VLAN configuration in the system. By default
                 this is disabled.";
       }

        leaf vn-untagged-vlan {
            type base-cmn:vlan-id;
            description
                "This is the VLAN id that will be used when untagged member interfaces
                 are added to virtual network. This VLAN will be used exclusively for
                 untagged interfaces in virtual network. This VLAN cannot be used
                 for regular switching and forwarding purpose.";
        }

        description "Default VLAN configurations";
    }

    container link_bundle_control {
        leaf link-bundle-trigger-threshold {
            description
                "Threshold at which alarm for link bundle monitoring triggers
                at.";
            type dell-yang:percent;
            default "60";
        }
    }

    container lag-globals {
      leaf resilient-hash-enable {
        type boolean;
        default false;
        description "This is the global configuration that determines if resilient
              hashing is enabled.";
      }
      description "LAG global configuration attributes";
    }

    description "Extending the interfaces container to add Dell proprietary attributes";
  }

  augment "/if:interfaces/if:interface" {

    leaf mtu {
      type uint32;
      default "1532";
      description
        "The MTU of the interface.";
    }
    leaf phys-address {
        type yang:phys-address;
        description
          "The interface's address at its protocol sub-layer.";
    }
    leaf mac-learn {
        type base-if:mac-learn-mode;
        default "HW";
        description "MAC address learning mode for the port or VLAN/VXLAN interface.";
    }

    leaf eee {
        type uint32;
        description
            "EEE (802.3az) state for this interface";
    }
    leaf tx-idle-time {
        type uint16;
        description
            "Tx idle time";
    }
    leaf tx-wake-time {
        type uint16;
        description
            "Tx wake time";
    }
    leaf vrf-name {
        type string;
        description "VRF/Namespace name";
    }
    description "The following attributes are common to all interface types.";
  }

  // Phy and LAG
  augment "/if:interfaces/if:interface" {
    when "if:type = 'ianaift:ethernetCsmacd' or if:type = 'ianaift:ieee8023adLag'";

    leaf mode {
      type base-if:mode;
      default "MODE_L2";
      description "L2, L2_HYBRID or L3";
    }
    leaf load-interval {
        type uint32 {
          range "30..299";
        }
        default "299";
        description
          "Traffic sampling interval for the interface";
    }

    leaf ingress-split-horizon-id{
        type uint32;
        default "0";
        description
        "Ingress split horizon ID of the interface. This will not apply to the actual
         interface but to all sub interfaces which are part of 1D bridge whose parent
         interface is this interface. If ingress split horizon id of ingress sub
         interface is equal to egress split horizon id of egress sub interface,
         then packets should be discarded";
    }

    leaf egress-split-horizon-id{
        type uint32;
        default "0";
        description
        "Egress split horizon ID of the interface. This will not apply to the actual
         interface but to all sub interfaces which are part of 1D bridge whose parent
         interface is this interface. If ingress split horizon id of ingress sub
         interface is equal to egress split horizon id of egress sub interface,
         then packets should be discarded";
    }

    description "Extending interfaces object to include attributes common to PHY and LAG
                 interfaces";
  }

  // Phy specific
  augment "/if:interfaces/if:interface" {
        when "if:type = 'ianaift:ethernetCsmacd' or if:type = 'base-if:management'
             or  if:type = 'ianaift:fibreChannel'";

        leaf duplex {
          type base-cmn:duplex-type;
          default "auto";
          description
                "The interface duplex";
        }
        leaf auto-negotiation {
          type boolean;
          description
                "Link auto-negotiation setting on the interface";
        }
        leaf negotiation {
            type enumeration {
                enum "auto" {
                  value 1;
                }
                enum "on" {
                  value 2;
                }
                enum "off" {
                  value 3;
                }
            }
            description
                "Negotiation setting on the interface";
        }
        leaf speed {
          type base-if:speed;
          default "AUTO";
          description
                "Should be removed and used from ietf yang model";
        }
        description
         "Extending the interfaces container to add attributes common to different phy interface types";
  }


    augment "/if:interfaces/if:interface" {
        when "if:type = 'base-if:vlanSubInterface'";

        leaf vlan-id {
            type base-cmn:vlan-id;
            description "VLAN ID of the sub-interface.";
        }
        description "VLAN sub-interface is created for the combination of Physical
                      interface/LAG and Vlan Id.";
    }


  augment "/if:interfaces-state/if:interface" {

    leaf ip-mtu {
      type uint32;
      description
        "The IP MTU of the interface.";
    }
    description "Extending the interfaces-state object to include attributes common to all interface types.";
  }

    augment "/if:interfaces-state/if:interface" {
        when "if:type = 'ianaift:ethernetCsmacd' or if:type = 'base-if:management'
             or  if:type = 'ianaift:fibreChannel'";

        leaf configured-fec {
          type base-cmn:fec-type;
          description
             " If user configures the fec-type to auto, the configured fec-type in hw is based
               on the media type. This leaf 'configured-fec' reflects the value set in hw
               for auto. The other leaf /if:interfaces-state/if:interface/fec is the
               negotiated value. Forward Error Correction type auto, disable or FEC type.
               It is only applicable for 100G, 50G and 25G interfaces and it will throw Error
               on any other type of interfaces. BASE module sets the default configuration
               based on the support by plugged-in media and the Hardware";
        }

        leaf duplex {
          type base-cmn:duplex-type;
          description
                "The interface duplex";
        }
        leaf auto-negotiation {
          type boolean;
          default "true";
          description
                "Link auto-negotiation setting on the interface";
        }
        leaf-list supported-speed {
            type base-if:speed;
            description "list of supported speeds in the interface";
        }
        leaf max-speed {
            type base-if:speed;
            description
                "maximum speed that can be configured for the interface";
        }

        leaf discontinuity-time-timeticks {
          type yang:timestamp;
          description
                 "The time on the most recent occasion at which any one or
                  more of this interface's counters suffered a
                  discontinuity.  If no such discontinuities have occurred
                  since the last re-initialization of the local management
                  subsystem, then this node contains the time the local
                  management subsystem re-initialized itself.";
        }

        leaf supported-autoneg {
            type base-if:supported-autoneg;
            description "Supported auto-negotiation value for the interface.";
        }
        description
         "Extending the interfaces-state container add attributes common to different phy interface types";
    }

  // LAG specfic
  augment "/if:interfaces/if:interface" {
        when "if:type = 'ianaift:ieee8023adLag'";

        leaf min-links {
          type uint32 {
            range "1..32";
          }
          default "1";
          description
                "Minimum number of members in port channel group";
        }

        leaf lag-mode {
          type base-if:lag-mode-type;
          default "STATIC";
          description "Mode of LAG to be create static LAG or dynamic LAG";
        }

        list member-ports {
          key "name";
          leaf name {
            type if:interface-ref;
            must "/if:interfaces/if:interface[if:name = current()]"
             +   "/if:type = 'ianaift:ethernetCsmacd'" {
              error-message
                "Only Ethernet interfaces can be added as member ports to a port-channel!";
            }
            description "interface name";
          }
          leaf lacp-mode {
            type base-if:lacp-mode-type;
            must "../../dell-if:lag-mode = 'DYNAMIC'"  {
            error-message
                "the mode is not compatible with the existing member(s)";
            description
                    "lacp mode";
            }
            description
                    "lacp mode";
          }
          description
                "This has member interfaces";
        }

        leaf link-bundle-monitor {
            type boolean;
            description
                "Enable/Disable link bundle monitoring";
        }
        description "This extension is focused on LAG attributes.";
  }

  // LAG specfic - state
  augment "/if:interfaces-state/if:interface" {
        when "if:type = 'ianaift:ieee8023adLag'";

        leaf lag-mode {
          type base-if:lag-mode-type;
          default "STATIC";
          description "Mode of LAG configured.";
        }
        description "This extension is focused on LAG state attributes.";
  }

  /* Ethernet specific */
  augment "/if:interfaces/if:interface" {
    when "if:type = 'ianaift:ethernetCsmacd'";

    leaf fec {
      type base-cmn:fec-type;
      description
              "Forward Error Correction type auto, disable or FEC type.
               It is only applicable for 100G, 50G and 25G interfaces and it will throw Error
               on any other type of interfaces. BASE module sets the default configuration
               based on the support by plugged-in media and the Hardware";
    }
    leaf oui {
       type uint32 {
         range "0..16777215";
       }
       description
          " Organisationally Unique Identifier for vendor Identification.
            It is only applicable for 25G and 50G interfaces. Allowed range is
            0 to 0xffffff and default value is 25G Consortium OUI 0x6A737D.
            OUI configuration should be same for all 25G interface in a front panel port";
    }
    description
         "Extending the interfaces container to add Ethernet specific attributes";
  }

  augment "/if:interfaces-state/if:interface" {
    when "if:type = 'ianaift:ethernetCsmacd'";

    leaf fec {
      type base-cmn:fec-type;
      description
              "Forward Error Correction type auto, disable or FEC type.
               It is only applicable for 100G, 50G and 25G interfaces";
    }
    leaf oui {
       type uint32 {
         range "0..16777215";
       }
       description
          " Organisationally Unique Identifier for vendor Identification.
            It is only applicable for 25G and 50G interfaces. Allowed range is
            0 to 0xffffff and default value is 25G Consortium OUI 0x6A737D";
    }
    description
         "Extending the interfaces-state container to add Ethernet specific attributes";
  }
  // VLAN specfic
  augment "/if:interfaces/if:interface" {
    when "if:type = 'ianaift:l2vlan' or if:type = 'ianaift:l3ipvlan'";

    leaf enable-statistics {
      type boolean;
      description "Enable/Disable statistics";
    }

    leaf learning-mode {
      type boolean;
            description "Enable/Disable MAC learning per VLAN";
    }

    leaf vlan-type {
      type base-if:vlan-type;
      default "DATA";
      description "VLAN type (data/management)";
    }

    leaf vlan-mode {
      type base-if:mode;
      description "VLAN mode can be change to L3 when global scaled-VLAN config is enabled.
      If global scaled-VLAN is disabled then VLAN-mode is not taken in account.";
    }

    leaf-list tagged-ports {
      type if:interface-ref;
      must "/if:interfaces/if:interface[if:name = current()]"
         + "/dell-if:mode = 'MODE_L2HYBRID'"
         + " or (/if:interfaces/if:interface[if:name = current()]"
         + "/if:type = 'base-if:management')" {
        error-message
          "Interface being added (to VLAN) is not in switchport mode trunk!";
      }
      must "(../dell-if:vlan-type = 'DATA'"
         + " and /if:interfaces/if:interface[if:name = current()]"
         + "/if:type != 'base-if:management') or (../dell-if:vlan-type = 'MANAGEMENT')" {
        error-message
          "Data VLAN cannot have management interface as member. Vlan type can be changed only when it has no members!";
      }
      must "(../dell-if:vlan-type = 'MANAGEMENT'"
         + " and /if:interfaces/if:interface[if:name = current()]"
         + "/if:type = 'base-if:management') or (../dell-if:vlan-type = 'DATA')" {
        error-message
          "Management VLAN cannot have data interface as member. Vlan type can be changed only when it has no members!";
      }
      description "VLAN tagged ports";
    }

    leaf-list untagged-ports {
      type if:interface-ref;
      must "/if:interfaces/if:interface[if:name = current()]"
         + "/dell-if:mode = 'MODE_L2' or
            /if:interfaces/if:interface[if:name = current()]"
         + "/dell-if:mode = 'MODE_L2HYBRID'"
         + " or (/if:interfaces/if:interface[if:name = current()]"
         + "/if:type = 'base-if:management')" {
        error-message
          "Interface being added (to VLAN) is not in switchport mode access or trunk!";
      }
      must "(../dell-if:vlan-type = 'DATA'"
         + " and /if:interfaces/if:interface[if:name = current()]"
         + "/if:type != 'base-if:management') or (../dell-if:vlan-type = 'MANAGEMENT')" {
        error-message
          "Data VLAN cannot have management interface as member. Vlan type can be changed only when it has no members!";
      }
      must "(../dell-if:vlan-type = 'MANAGEMENT'"
         + " and /if:interfaces/if:interface[if:name = current()]"
         + "/if:type = 'base-if:management') or (../dell-if:vlan-type = 'DATA')" {
        error-message
          "Management VLAN cannot have data interface as member. Vlan type can be changed only when it has no members!";
      }
      description "VLAN untagged ports";
    }
    leaf parent-bridge {
      type string;
      description " This is an optional configuration.
                    The VLAN becomes part of the bridge domain indicated by the parent-bridge. All its tagged and untagged
                    members becomes part of the bridge domain. VLAN inherits L3 properties of the parent-bridge.
                    IP address and route info should be configured on the parent bridge only.";
    }
    description
         "Extending the interfaces container to add VLAN specific attributes";
  }

  // VXLAN specfic
  augment "/if:interfaces/if:interface" {
    when "if:type = 'base-if:vxlan'";

        leaf vni {
            type base-cmn:vni;
            description "VXLAN Network Identifier";
        }

        container source-ip {
            uses base-cmn:ip;
            description "VXLAN Tunnel Source IP Address";
        }

        uses base-if:vn-remote-endpoints {
            description "List of remote VTEP endpoints associated with this VXLAN. Remote endpoints
                          configured in the flooding domain using this model.";
            //Qualifiers Observed : list of all remote endpoints associated with the VTEP."
            //Qualifiers Target: List of remote endpoints associated with this vtep's flooding domain"
        }
        description
         "Extending the interfaces container to add VxLAN specific attributes";
    }

  //MacVLAN or VLAN sub interface specific
  augment "/if:interfaces/if:interface" {
    when "if:type = 'base-if:macvlan' or if:type = 'base-if:vlanSubInterface'";

    leaf parent-interface {
      type if:interface-ref;
      description "The interface name from which macVLAN interface is to be created";
    }
    description "Macvlan Interface configuration attributes";
  }

  augment "/if:interfaces-state/if:interface" {
    when "if:type = 'base-if:macvlan' or if:type = 'base-if:vlanSubInterface'";

    leaf parent-interface {
      type if:interface-ref;
      description "The interface name from which macvlan interface is to be created";
    }
    description "Macvlan Interface configuration attributes";
  }

  augment "/if:interfaces-state/if:interface" {
    when "if:type = 'base-if:vxlan'";

        leaf vni {
            type base-cmn:vni;
            description "VXLAN Network Identifier";
        }

        container source-ip {
            uses base-cmn:ip;
            description "VXLAN Tunnel Source IP Address";
        }

        uses base-if:vn-remote-endpoints {
            description "List of remote VTEP endpoints associated with this VXLAN. Remote endpoints
                          configured in the flooding domain using this model.";
            //Qualifiers Observed : list of all remote endpoints associated with the VTEP."
            //Qualifiers Target: List of remote endpoints associated with this vtep's flooding domain"
        }
    description "Extending the interfaces-state object to include VxLAN interface
                 specific configuration attributes";
  }

  augment "/if:interfaces-state/if:interface" {
   when "if:type = 'ianaift:fibreChannel'";

       leaf bb-credit {
           type uint32;
           description "The Buffer-to-Buffer Credit allocation";
       }

       leaf fc-mtu {
           type uint32;
           description
              "FC port MTU";
       }
       leaf npu-speed {
           type base-if:speed;
           description "Port's NPU Speed";
       }
       description
         "Extending the interfaces-state container to add Fibre-Channel specific attributes";
  }

  augment "/if:interfaces-state/if:interface" {
    when "if:type = 'base-if:management'";

       leaf bind-ni-name {
         type leafref {
           path "/ni:network-instances/ni:network-instance/ni:name";
         }
         description
           "Network Instance to which an interface is bound.";
       }
    description "Interface state attributes applicable for
                 ethernet/management/LAG/L2VLAN/L3VLAN interfaces.";
  }


  augment "/if:interfaces-state/if:interface/if:statistics" {
      when "../if:type = 'ianaift:ethernetCsmacd'";

        leaf if-in-vlan-discards {
            type yang:counter64;
            description "Number of interface incoming VLAN discarded packets";
        }
        leaf if-out-qlen {
            type yang:counter64;
            description "Number of interface outgoing queue length";
        }
        leaf ether-drop-events {
            type yang:counter64;
            description "Number of ethernet drop events";
        }
        leaf ether-multicast-pkts {
            type yang:counter64;
            description "Number of ethernet multicast packets";
        }
        leaf ether-broadcast-pkts {
            type yang:counter64;
            description "Number of ethernet broadcast packets";
        }
        leaf ether-undersize-pkts {
            type yang:counter64;
            description "Number of ethernet undersize packets";
        }
        leaf ether-fragments {
            type yang:counter64;
            description "Number of ethernet fragments";
        }
        leaf ether-oversize-pkts {
            type yang:counter64;
            description "Number of ethernet stats oversize packets";
        }
        leaf ether-rx-oversize-pkts {
            type yang:counter64;
            description "Number of ethernet received oversize packets";
        }
        leaf ether-tx-oversize-pkts {
            type yang:counter64;
            description "Number of ethernet transmitted oversize packets";
        }
        leaf ether-jabbers {
            type yang:counter64;
            description "Number of ethernet stats jabbers";
        }
        leaf ether-octets {
            type yang:counter64;
            description "Number of ethernet stats octets";
        }
        leaf ether-pkts {
            type yang:counter64;
            description "Number of ethernet stats packets";
        }
        leaf ether-collisions {
            type yang:counter64;
            description "Number of ethernet stats collisions";
        }
        leaf ether-crc-align-errors {
            type yang:counter64;
            description "Number of ethernet stats crc align errors";
        }
        leaf ether-tx-no-errors {
            type yang:counter64;
            description "Number of ethernet stats tx no errors";
        }
        leaf ether-rx-no-errors {
            type yang:counter64;
            description "Number of ethernet stats rx no errors";
        }
        leaf green-discard-dropped-packets {
            type yang:counter64;
            description "Number of WRED green packet count";
        }
        leaf green-discard-dropped-bytes {
            type yang:counter64;
            description "Number of WRED green byte count";
        }
        leaf yellow-discard-dropped-packets {
            type yang:counter64;
            description "Number of WRED yellow packet count";
        }
        leaf yellow-discard-dropped-bytes {
            type yang:counter64;
            description "Number of WRED yellow packet count";
        }
        leaf red-discard-dropped-packets {
            type yang:counter64;
            description "Number of WRED red packet count";
        }
        leaf red-discard-dropped-bytes {
            type yang:counter64;
            description "Number of WRED red packet count";
        }
        leaf discard-dropped-packets {
            type yang:counter64;
            description "Number of WRED dropped packet count";
        }
        leaf discard-dropped-bytes {
            type yang:counter64;
            description "Number of WRED dropped packet bytes";
        }
        leaf ecn-marked-packets {
            type yang:counter64;
            description "Number of ECN-marked packets";
        }
        leaf ether-in-pkts-64-octets {
            type yang:counter64;
            description "Number of Ethernet receive packets of 64 octets";
        }
        leaf ether-in-pkts-65-to-127-octets {
            type yang:counter64;
            description "Number of Ethernet receive packets of 65 to 127 octets";
        }
        leaf ether-in-pkts-128-to-255-octets {
            type yang:counter64;
            description "Number of Ethernet receive packets of 128 to 255 octets";
        }
        leaf ether-in-pkts-256-to-511-octets {
            type yang:counter64;
            description " Number of Ethernet receive packets of 256 to 511 octets";
        }
        leaf ether-in-pkts-512-to-1023-octets {
            type yang:counter64;
            description "Number of Ethernet receive packets of 512 to 1023 octets";
        }
        leaf ether-in-pkts-1024-to-1518-octets {
            type yang:counter64;
            description "Number of Ethernet receive packets of 1024 to 1518 octets";
        }
        leaf ether-in-pkts-1519-to-2047-octets {
            type yang:counter64;
            description "Number of Ethernet receive packets of 1519 to 2047 octets";
        }
        leaf ether-in-pkts-2048-to-4095-octets {
            type yang:counter64;
            description "Number of Ethernet receive packets of 2047 to 4095 octets";
        }
        leaf ether-in-pkts-4096-to-9216-octets {
            type yang:counter64;
            description "Number of Ethernet receive packets of 4096 to 9216 octets";
        }
        leaf ether-in-pkts-9217-to-16383-octets {
            type yang:counter64;
            description "Number of Ethernet receive packets of 9217 to 16383 octets";
        }
        leaf ether-out-pkts-64-octets {
            type yang:counter64;
            description "Number of Ethernet transmit packets of 64 octets";
        }
        leaf ether-out-pkts-65-to-127-octets {
            type yang:counter64;
            description "Number of Ethernet transmit packets of 65 to 127 octets";
        }
        leaf ether-out-pkts-128-to-255-octets {
            type yang:counter64;
            description "Number of Ethernet transmit packets of 128 to 255 octets";
        }
        leaf ether-out-pkts-256-to-511-octets {
            type yang:counter64;
            description " Number of Ethernet transmit packets of 256 to 511 octets";
        }
        leaf ether-out-pkts-512-to-1023-octets {
            type yang:counter64;
            description "Number of Ethernet transmit packets of 512 to 1023 octets";
        }
        leaf ether-out-pkts-1024-to-1518-octets {
            type yang:counter64;
            description "Number of Ethernet transmit packets of 1024 to 1518 octets";
        }
        leaf ether-out-pkts-1519-to-2047-octets {
            type yang:counter64;
            description "Number of Ethernet transmit packets of 1519 to 2047 octets";
        }
        leaf ether-out-pkts-2048-to-4095-octets {
            type yang:counter64;
            description "Number of Ethernet transmit packets of 2047 to 4095 octets";
        }
        leaf ether-out-pkts-4096-to-9216-octets {
            type yang:counter64;
            description "Number of Ethernet transmit packets of 4096 to 9216 octets";
        }
        leaf ether-out-pkts-9217-to-16383-octets {
            type yang:counter64;
            description "Number of Ethernet transmit packets of 9217 to 16383 octets";
        }
        leaf current-occupancy-bytes {
            type yang:gauge64;
            description "Current port occupancy in bytes";
        }
        leaf watermark-bytes {
            type yang:gauge64;
            description "port occupancy watermark in bytes";
        }
        leaf shared-current-occupancy-bytes {
            type yang:gauge64;
            description "current port shared occupancy in bytes";
        }
        leaf shared-watermark-bytes {
            type yang:gauge64;
            description "port shared coccupancy watermark in bytes";
        }
        leaf xoff-room-current-occupancy-bytes {
            type yang:gauge64;
            description "current port xoff room occupancy in bytes";
        }
        leaf pause-rx-pkts {
            type yang:counter64;
            description "number of pause frames received on the port";
        }
        leaf pause-tx-pkts{
            type yang:counter64;
            description "number of pause frames transmitted on the port";
        }
        leaf pfc-0-rx-pkts{
            type yang:counter64;
            description "PFC 0 RX packet counter";
        }
        leaf pfc-0-tx-pkts{
            type yang:counter64;
            description "PFC 0 TX packet counter";
        }
        leaf pfc-1-rx-pkts{
            type yang:counter64;
            description "PFC 1 RX packet counter";
        }
        leaf pfc-1-tx-pkts{
            type yang:counter64;
            description "PFC 1 TX packet counter";
        }
        leaf pfc-2-rx-pkts{
            type yang:counter64;
            description "PFC 2 RX packet counter";
        }
        leaf pfc-2-tx-pkts{
            type yang:counter64;
            description "PFC 2 TX packet counter";
        }
        leaf pfc-3-rx-pkts{
            type yang:counter64;
            description "PFC 3 RX packet counter";
        }
        leaf pfc-3-tx-pkts{
            type yang:counter64;
            description "PFC 3 TX packet counter";
        }
        leaf pfc-4-rx-pkts{
            type yang:counter64;
            description "PFC 4 RX packet counter";
        }
        leaf pfc-4-tx-pkts{
            type yang:counter64;
            description "PFC 4 TX packet counter";
        }
        leaf pfc-5-rx-pkts{
            type yang:counter64;
            description "PFC 5 RX packet counter";
        }
        leaf pfc-5-tx-pkts{
            type yang:counter64;
            description "PFC 5 TX packet counter";
        }
        leaf pfc-6-rx-pkts{
            type yang:counter64;
            description "PFC 6 RX packet counter";
        }
        leaf pfc-6-tx-pkts{
            type yang:counter64;
            description "PFC 6 TX packet counter";
        }
        leaf pfc-7-rx-pkts{
            type yang:counter64;
            description "PFC 7 RX packet counter";
        }
        leaf pfc-7-tx-pkts{
            type yang:counter64;
            description "PFC 7 TX packet counter";
        }
        leaf tx-lpi-count {
            type yang:counter64;
            description
                "Tx LPI event count";
        }
        leaf tx-lpi-duration {
            type yang:counter64;
            description
                "Tx LPI duration";
        }
        leaf rx-lpi-count {
            type yang:counter64;
            description
                "Rx LPI event count";
        }
        leaf rx-lpi-duration {
            type yang:counter64;
            description
                "Rx LPI duration";
        }
        leaf utilization-percentage {
            type uint8 {
                range "0..100";
            }
            description
                "Utilization of port in total LAG bandwidth.";
        }
        description "Interface counter attributes";

    }

  augment "/if:interfaces-state/if:interface/if:statistics" {
      when "../if:type = 'ianaift:ethernetCsmacd' or ../if:type = 'ianaift:ieee8023adLag' or "
            + "../if:type = 'ianaift:fibreChannel'";

      leaf in-bit-rate {
          type yang:gauge64;
          units "bits/second";
          description
              "Rate of ingress octets";
      }
      leaf in-pkt-rate {
          type yang:gauge64;
          units "packets/second";
          description
              "Rate of ingress packets";
      }
      leaf in-port-utilization {
          type uint8 {
              range "0..100";
          }
          description
              "Rate of in line usage";
      }
      leaf out-bit-rate {
          type yang:gauge64;
          units "bits/second";
          description
              "Rate of egress octets";
      }
      leaf out-pkt-rate {
          type yang:gauge64;
          units "packets/second";
          description
              "Rate of egress packets";
      }
      leaf out-port-utilization {
          type uint8 {
              range "0..100";
          }
          description
              "Rate of out line usage";
      }
  }


    augment "/if:interfaces-state/if:interface/if:statistics" {
        when "../if:type = 'ianaift:l2vlan' or ../if:type = 'ianaift:l3ipvlan' or "
           + "../if:type = 'ianaift:softwareLoopback' or ../if:type = 'base-if:management' or "
           + "../if:type = 'ianaift:ethernetCsmacd' or ../if:type = 'ianaift:ieee8023adLag'";

        leaf in-pkts {
          type yang:counter64;
          description
            "Total number of incoming packets";
        }
        leaf out-pkts {
          type yang:counter64;
          description
            "Total number of outgoing packets";
        }
        description
         "Extending the interfaces-state container to add VLAN/loopback/mgmt interface specific attributes";
    }

    augment "/if:interfaces-state/if:interface/if:statistics" {
        when "../if:type = 'ianaift:fibreChannel'";

        leaf rx-bytes {
          type yang:counter64;
          description
            "Total received bytes";
        }
        leaf rx-frames {
          type yang:counter64;
          description
            "Total number of good frames received";
        }
        leaf rx-ucast-pkts {
          type yang:counter64;
          description
            "Total number of unicast packets received";
        }
        leaf rx-bcast-pkts {
          type yang:counter64;
          description
            "Total number of broadcast packets received";
        }
        leaf rx-invalid-crc {
          type yang:counter64;
          description
            "Total number of packets(includes Class 2,3 and F) received
                with invalid CRC";
        }
        leaf rx-frame-too-long {
          type yang:counter64;
          description
            "Total number (includes Class 2, 3, F) of too long frames received";
        }
        leaf rx-frame-truncated {
          type yang:counter64;
          description
            "Total number (includes Class 2, 3 and F)of truncated frames received";
        }
        leaf rx-link-fail {
          type yang:counter64;
          description
            "Total number of link fail received";
        }
        leaf rx-loss-sync {
          type yang:counter64;
          description
            "Total number of loss synchronizations received";
        }
        leaf class2-rx-good-frames {
          type yang:counter64;
          description
            "Total number of class 2 good frames received";
        }
        leaf class3-rx-good-frames {
          type yang:counter64;
          description
            "Total number of class 3 good frames received";
        }
        leaf rx-bb-credit0 {
          type yang:counter64;
          description
            "The number of transitions into the rx BB credit zero state";
        }
        leaf rx-bb-credit0_drop {
          type yang:counter64;
          description
            "The number packets dropped due to BB credit 0";
        }
        leaf rx-prim-seq-err {
          type yang:counter64;
          description
            "Total number of frames with primitive sequence Protocol errors received";
        }
        leaf rx-lip-count {
          type yang:counter64;
          description
            "Total number of LIP(Loop Initialization Primitive Sequence) Count";
        }
        leaf tx-bytes {
          type yang:counter64;
          description
            "Total transmit bytes";
        }
        leaf tx-frames {
          type yang:counter64;
          description
            "Total number of frames transmitted";
        }
        leaf tx-ucast-pkts {
          type yang:counter64;
          description
            "Total number of unicast packets transmitted";
        }
        leaf tx-bcast-pkts {
          type yang:counter64;
          description
            "Total number of non-unicast packets transmitted";
        }
        leaf class2-tx-frames {
          type yang:counter64;
          description
            "Total number of class 2 frames transmitted";
        }
        leaf class3-tx-frames {
          type yang:counter64;
          description
            "Total number of class 3 frames transmitted";
        }
        leaf tx-bb-credit0 {
          type yang:counter64;
          description
            "FC port full buffer counter(0 transmit BB credit)";
        }
        leaf tx-oversize_frames {
          type yang:counter64;
          description
            "Total number (including Class 2, 3 and F) of oversize packets
                transmitted";
        }
        leaf total-errors {
          type yang:counter64;
          description
            "Total number of errors, including rx and tx";
        }
        description
         "Extending the interfaces-state container to add various Fibre Channel statistics";
    }

    augment "/if:interfaces-state/if:interface/if:statistics" {
        when "../if:type = 'ianaift:ieee8023adLag'";

        leaf link-bundle-monitoring-alarm {
            type boolean;
            description
                "Indicates whether or not the threshold for link bundle monitoring
                has been passed. Only valid if link bundle monitoring is active
                for the link bundle.";
        }
        description
         "Extending the interfaces statistics container to provide link bundle alaram status";
    }

   grouping ipv4-stats {
       leaf ip-in-receives {
            type yang:counter64;
            description "The total number of input datagrams received from
                      interfaces, including those received in error.";
            reference
              "RFC 1213: Network Management of TCP/IP-based internets";
        }

        leaf ip-in-hdr-errors {
            type yang:counter64;
            description "The number of input datagrams discarded due to
                      errors in their IP headers, including bad
                      checksums, version number mismatch, other format
                      errors, time-to-live exceeded, errors discovered
                      in processing their IP options, etc.";
            reference
              "RFC 1213: Network Management of TCP/IP-based internets";
        }

        leaf ip-in-discards {
            type yang:counter64;
            description "The number of input IP datagrams for which no
                      problems were encountered to prevent their
                      continued processing, but which were discarded
                      (e.g., for lack of buffer space).  Note that this
                      counter does not include any datagrams discarded
                      while awaiting re-assembly.";
            reference
              "RFC 1213: Network Management of TCP/IP-based internets";
        }

        leaf ip-in-forw-datagrams {
            type yang:counter64;
            description "The number of input datagrams for which this
                      entity was not their final IP destination, as a
                      result of which an attempt was made to find a
                      route to forward them to that final destination.
                      In entities which do not act as IP Gateways, this
                      counter will include only those packets which were
                      Source-Routed via this entity, and the Source-
                      Route option processing was successful.";
            reference
              "RFC 1213: Network Management of TCP/IP-based internets";
        }

        description "Set of statistics pertaining to ipv4 packets received in the interface";
   }

   grouping ipv6-stats {
       leaf ipv6-in-receives {
            type yang:counter64;
            description "The total number of input datagrams received by
                the interface, including those received in error.";
            reference
              "RFC 2465: Management Information Base for IP Version 6";
        }

        leaf ipv6-in-hdr-errors {
            type yang:counter64;
            description "The number of input datagrams discarded due to
                errors in their IPv6 headers, including version
                number mismatch, other format errors, hop count
                exceeded, errors discovered in processing their
                IPv6 options, etc.";
            reference
              "RFC 2465: Management Information Base for IP Version 6";
        }

        leaf ipv6-in-addr-errors {
            type yang:counter64;
            description "The number of input datagrams discarded because
                the IPv6 address in their IPv6 header's destination
                field was not a valid address to be received at
                this entity.  This count includes invalid
                addresses (e.g., ::0) and unsupported addresses
                (e.g., addresses with unallocated prefixes).  For
                entities which are not IPv6 routers and therefore
                do not forward datagrams, this counter includes
                datagrams discarded because the destination address
                was not a local address.";
            reference
              "RFC 2465: Management Information Base for IP Version 6";
        }

        leaf ipv6-in-discards {
            type yang:counter64;
            description "The number of input IPv6 datagrams for which no
                problems were encountered to prevent their
                continued processing, but which were discarded
                (e.g., for lack of buffer space).  Note that this
                counter does not include any datagrams discarded
                while awaiting re-assembly.";
            reference
              "RFC 2465: Management Information Base for IP Version 6";
        }

        leaf ipv6-out-discards {
            type yang:counter64;
            description "The number of output IPv6 datagrams for which no
                 problem was encountered to prevent their
                 transmission to their destination, but which were
                 discarded (e.g., for lack of buffer space).  Note
                 that this counter would include datagrams counted
                 in ipv6IfStatsOutForwDatagrams if any such packets
                 met this (discretionary) discard criterion.";
            reference
              "RFC 2465: Management Information Base for IP Version 6";
        }

        leaf ipv6-out-forw-datagrams {
            type yang:counter64;
            description "The number of output datagrams which this
                entity received and forwarded to their final
                destinations.  In entities which do not act
                as IPv6 routers, this counter will include
                only those packets which were Source-Routed
                via this entity, and the Source-Route
                processing was successful.  Note that for
                a successfully forwarded datagram the counter
                of the outgoing interface is incremented.";
            reference
              "RFC 2465: Management Information Base for IP Version 6";
        }

        leaf ipv6-in-mcast-pkts {
            type yang:counter64;
            description "The number of multicast packets received
                 by the interface";
            reference
              "RFC 2465: Management Information Base for IP Version 6";
        }

        leaf ipv6-out-mcast-pkts {
            type yang:counter64;
            description "The number of multicast packets transmitted
                 by the interface";
            reference
              "RFC 2465: Management Information Base for IP Version 6";
        }
        description "Set of statistics pertaining to ipv6 packets received in the interface";
   }

    augment "/if:interfaces-state/if:interface/if:statistics" {

        leaf counters-last-clear {
            type yang:timeticks;
            description
                "Time since last clear of counters";
        }
    }

    augment "/if:interfaces-state/if:interface/if:statistics" {
        when "../if:type = 'ianaift:ethernetCsmacd'";

        leaf alignment-errors {
            type yang:counter64;
            description "A count of frames received on a particular
                       interface that are not an integral number of
                       octets in length and do not pass the FCS check.";
            reference
              "RFC 3635: EtherLike-MIB";
        }

        leaf fcs-errors {
            type yang:counter64;
            description "A count of frames received on a particular
                       interface that are an integral number of octets
                       in length but do not pass the FCS check.";
            reference
              "RFC 3635: EtherLike-MIB";
        }

        leaf single-collision-frames {
            type yang:counter64;
            description "A count of frames that are involved in a single
                       collision, and are subsequently transmitted
                       successfully.";
            reference
              "RFC 3635: EtherLike-MIB";
        }

        leaf multiple-colision-frames {
            type yang:counter64;
            description "A count of frames that are involved in more
                         than one collision and are subsequently
                         transmitted successfully.";
            reference
              "RFC 3635: EtherLike-MIB";
        }

        leaf sqe-test-errors {
            type yang:counter64;
            description "A count of times that the SQE TEST ERROR
                       is received on a particular interface.";
            reference
              "RFC 3635: EtherLike-MIB";
        }

        leaf deferred-transmissions {
            type yang:counter64;
            description "A count of frames for which the first
                       transmission attempt on a particular interface
                       is delayed because the medium is busy.";
            reference
              "RFC 3635: EtherLike-MIB";
        }

        leaf late-collisions {
            type yang:counter64;
            description "The number of times that a collision is
                       detected on a particular interface later than
                       one slotTime into the transmission of a packet.";
            reference
              "RFC 3635: EtherLike-MIB";
        }

        leaf excessive-collisions {
            type yang:counter64;
            description "A count of frames for which transmission on a
                       particular interface fails due to excessive
                       collisions.";
            reference
              "RFC 3635: EtherLike-MIB";
        }

        leaf internal-mac-transmit-errors {
            type yang:counter64;
            description "A count of frames for which transmission on a
                       particular interface fails due to an internal
                       MAC sublayer transmit error.";
            reference
              "RFC 3635: EtherLike-MIB";
        }

        leaf carrier-sense-errors {
            type yang:counter64;
            description "The number of times that the carrier sense
                       condition was lost or never asserted when
                       attempting to transmit a frame on a particular
                       interface.";
            reference
              "RFC 3635: EtherLike-MIB";
        }

        leaf frame-too-long {
            type yang:counter64;
            description "A count of frames received on a particular
                       interface that exceed the maximum permitted
                       frame size.";
            reference
              "RFC 3635: EtherLike-MIB";
        }

        leaf internal-mac-receive-errors {
            type yang:counter64;
            description "A count of frames for which reception on a
                       particular interface fails due to an internal
                       MAC sublayer receive error.";
            reference
              "RFC 3635: EtherLike-MIB";
        }

        leaf symbol-errors {
            type yang:counter64;
            description "This is a read-only counter that logs various carrier events
                         on an interface depending on its speed and type.
                         Eg. 'invalid data symbol' (100 Mb/s speed),
                         'Data reception error'(1000 Mb/s speed and half-duplex),
                         'Carrier extend error'(1000 Mb/s speed and full-duplex),
                         For more details refer RFC 3635 Section 4.";
            reference
              "RFC 3635: EtherLike-MIB";
        }

        leaf in-unknown-opcodes {
            type yang:counter64;
            description "A count of MAC Control frames received on this
                       interface that contain an opcode that is not
                       supported by this device.";
            reference
              "RFC 3635: EtherLike-MIB";
        }

        leaf eee-last-clear {
            type yang:timeticks;
            description
                "Time since last clear of EEE counters";
        }

        uses ipv4-stats;
        uses ipv6-stats;

        description "Extending interfaces-state object to include PHY interface specific attributes";
    }

    rpc clear-counters {
      description "RPC for clearing interface counters. Input can be :
                   1. Single interface name (or ifindex for base)
                   2. All interfaces
                   3. All interfaces of a particular type";

      // ATTRIBUTE PATH  : dell-if/clear-counters
      // ==============
      //
      // INPUT           : dell-if/clear-counters/input/all-intf  (specify the interface type),
      // =====          OR dell-if/clear-counters/input/ifname    (specify the interface name),
      //                OR dell-if/clear-counters/input/if-index  (specify the if-index).
      //
      // OUTPUT          : None
      // ======

      input {
        choice intf-choice {
          case all-intf-case {
            leaf all-intf {
              type enumeration {
                enum "ALL" {
                  value 1;
                }
                enum "ALL-ETH" {
                  value 2;
                }
                enum "ALL-LAG" {
                  value 3;
                }
                enum "ALL-VLAN" {
                  value 4;
                }
                enum "ALL-LOOPBACK" {
                  value 5;
                }
                enum "ALL-MGMT" {
                  value 6;
                }
                enum "ALL-FC" {
                  value 7;
                }
                enum "ALL-VNI" {
                    value 8;
                }
                enum "ALL-VLANSUBINTERFACE" {
                    value 9;
                }
              }
              description "All interfaces of all types or single type";
            }
          }
          case ifname-case {
            leaf ifname {
              type if:interface-ref;
              description "Interface name";
            }
          }
          case ifindex-case {
            leaf ifindex {
              type int32;
              description "Interface index";
            }
          }
          description "Different choices of values for interface-specific attributes";
        }
      }
    }

    rpc clear-eee-counters {
        description "RPC for clearing 802.3az (EEE)interface counters. Input will be :
                     all interfaces (all-intf = ALL), or
                     a single interface name (or ifindex for base)";

       // ATTRIBUTE PATH  : dell-if/clear-eee-counters
       // ==============
       //
       // INPUT           : dell-if/clear-eee-counters/input/all-intf (specify the interface type),
       // =====          OR dell-if/clear-eee-counters/input/ifname   (specify the interface name),
       //                OR dell-if/clear-eee-counters/input/if-index (specify the if-index).
       //
       // OUTPUT          : None
       // ======

        input {
            choice intf-choice {
                case all-intf-case {
                    leaf all-intf {
                        type enumeration {
                            enum "ALL" {
                                value 1;
                            }
                        }
                        description "All EEE interfaces";
                    }
                }
                case ifname-case {
                    leaf ifname {
                        type if:interface-ref;
                        description "Interface name";
                    }
                }
                case ifindex-case {
                    leaf ifindex {
                        type int32;
                        description "Interface index";
                    }
                }
                description "Different choices of values for 802.3az interface specific attributes";
            }
        }
    }

    rpc if-location-led {
        description
          "Set the led status of a specific interface";

        // ATTRIBUTE PATH  : dell-if/f-location-led
        // ==============
        //
        // INPUT           : dell-if/if-location-led/input/ifname  (specify the interface name),
        // =====             dell-if/if-location-led/input/led-on  (specify the led status),
        //
        // OUTPUT          : None
        // ======
        input {
          leaf ifname {
            type if:interface-ref;
            description
              "Interface name";
          }
          leaf led-on {
               type boolean;
               description "Indicates led state requested";
          }
        }
    }

    rpc clear-pause-counters {
        description "RPC for clearing LLFC/PFC interface counters. Input will be :
                     all interfaces (all-intf = ALL), or
                     a single interface name (or ifindex for base)";

       // ATTRIBUTE PATH  : dell-if/clear-pause-counters
       // ==============
       //
       // INPUT           : dell-if/clear-pause-counters/input/all-intf (specify the interface type),
       // =====          OR dell-if/clear-pause-counters/input/ifname   (specify the interface name),
       //                OR dell-if/clear-pause-counters/input/if-index (specify the if-index).
       //
       // OUTPUT          : None
       // ======

        input {
            choice intf-choice {
                case all-intf-case {
                    leaf all-intf {
                        type enumeration {
                            enum "ALL" {
                                value 1;
                            }
                        }
                        description "All ethernet and fiberchannel interfaces";
                    }
                }
                case ifname-case {
                    leaf ifname {
                        type if:interface-ref;
                        description "Interface name";
                    }
                }
                case ifindex-case {
                    leaf ifindex {
                        type int32;
                        description "Interface index";
                    }
                }
                description "Different choices of values for interface specific attributes";
            }
        }
    }
}
