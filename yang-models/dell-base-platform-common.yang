module dell-base-platform-common {

  namespace "http://www.dellemc.com/networking/os10/dell-base-platform-common";

  prefix "platform";

  import ietf-yang-types {
    prefix yang;
  }

  import dell-yang-types {
    prefix common;
  }

  import dell-base-common {
    prefix "base-cmn";
  }

  import dell-base-interface-common {
    prefix "base-if";
  }

  organization "Dell EMC";

  contact "http://www.dell.com/support";

  description "Common definitions for platform hardware

  Copyright (c) 2015-2019 by Dell EMC,

  All rights reserved.";

  revision 2018-09-24 {
    description "Adding enable/disable digital media monitoring.";
    reference "Network Platform Abstraction";
  }

  revision 2018-08-20 {
    description "Adding media attribute for wavelength in picometers. This was needed due to the ability of wavelengths to now be configured and read at the pico meter level.
                    The previous attribute for this field was an nanometer integer which caused in loss of precision";
    reference "Network Platform Abstraction";
  }

  revision 2018-06-26 {
    description "Adding back media attribute QSA28-expected.";
    reference "Network Platform Abstraction";
  }

  revision 2018-06-15 {
    description "Fixing IETF error for enum value type.";
    reference "Network Platform Abstraction";
  }

  revision 2018-05-31 {
    description "Added media attribute for qsa28-expected. This flag is used to note when QSA (which is optimized for SFP/SFP+) is used with SFP28. This is because SFP28 expects QSA28
                    and not QSA. ";
    reference "Networking Platform Abstraction";
  }

  revision 2018-05-18 {
    description "Added media attribute for media name. This name is used to refer to the particular media type
                 Added media attribute for category display string, which is used in 'show' commands";
    reference "Networking Platform Abstraction";
  }

  revision 2018-05-11 {
    description
      "Added 25G 5M DAC to list of supported media";
    reference "Network Platform Abstraction";
  }

  revision 2018-05-08 {
    description "Added media types for 100G ESR4, DWDM2, ER4 LITE, AOC, SR4 NOF, 40G BIDI, 10G BX10/40";
    reference "Networking Platform Abstraction";
  }

  revision 2018-04-19 {
    description "Added media attributes for:
                       Max media power: this is the theoretical upper bound for the power a device can draw form the port. This number does not change in realtime
                       Max port power: this is the maximum power that the port can allow a connected device to draw. If a device requires higher power, it is put in low power mode (idle)
                       Power limit flag: this flag states if the max media power exceeds the port power.
                       NOTE: if the power limit flag is set, the device cannot be expected to funtion normally as it will likely be put in idle mode";
    reference "Networking Platform Abstraction";
  }

  revision 2018-04-16 {
    description "Added media attributes for:
                       Default autoneg: for the default autoneg setting based on the media informatiom
                       Default FEC: for the default FEC (forward error correction) setting recommended for the media.
                       Note: The default values for Autoneg and FEC correspond to the default mode of operation of the media.
                             If multiple-mode-supported is true, then other values are supported as well.";
    reference "Networking Platform Abstraction";
  }

  revision 2018-04-03 {
    description "Added leaves for:
                 media cable length in centimeters: which extends the former integer leaf (meters). This allows fractional lengths to be represented,
                 lane count: which is useful for identifying how many lanes of transmission there are. For example SR vs SR4 has 1 vs 4 lanes respectively,
                 ESR media interfac: which is an additional interface to be supported,
                 separable connector flag: which tells if the transmission cable is separable from the transceiver module";
    reference "Networking Platform Abstraction";
  }

  revision 2018-03-27 {
    description "Added leaves for media connector, cable type, QSA adapter, device ready status.
                 Added QSA adapter type";
    reference "Networking Platform Abstraction";
  }

  revision 2018-03-20 {
    description "Some PSUs do not have fans - define a not-applicable enum fan-airflow-type for those cases.";
    reference "Networking Platform Abstraction";
  }

  revision 2018-03-07 {
    description "Added display string for media: this allow consistency since the display string to be provided by one source.
                 Added media connector type info which specifies the type of connector of the media inserted
                 Added media cable type for specifying the type of cable ";

    reference "Networking Platform Abstraction";
  }

  revision 2017-12-04 {
    description "Added platform fault grouping.";
    reference "Networking Platform Abstraction";
  }

  revision 2017-11-21 {
    description "Added leaf fabric id for hostsystem object";
    reference "Networking Platform Abstraction";
  }

  revision 2017-11-08 {
    description "Added power-monitor grouping for input power monitoring";
    reference "Networking Platform Abstraction";
  }

  revision 2017-10-06 {
    description "Added leaf for media channel count.";
    reference "Networking Platform Abstraction";
  }

  revision 2017-10-05 {
    description "Added leaf for media lockdown state.";
    reference "Networking Platform Abstraction";
  }

  revision 2017-10-02 {
    description "Added more QSFP28-DD media.";
    reference "Networking Platform Abstraction";
  }

  revision 2015-11-04 {
    description
      "Updated based on new guidelines for Yang Model update";
    reference "Networking Platform Abstraction";
  }

  revision 2015-05-20 {
    description
      "Added temperature control fault-value type";
    reference "Networking Platform Abstraction";
  }
  revision 2015-04-03 {
    description "Initial revision.";
    reference "Networking Platform Abstraction";
  }

  // An entity is any FRU within a chassis

  typedef entity-type {
    type enumeration {
      enum PSU {
        value 1;
        description "PSU (power supply unit)";
      }
      enum FAN_TRAY {
        value 2;
        description "Fan tray";
      }
      enum CARD {
        value 3;
        description "Card (Linecard, RPM)";
      }
    }
    description "Entity type";
  }

  typedef card-type-type {
    type uint32;
    description "Encoded value for type of card";
  }

  typedef fault-type {
    type enumeration {
      enum OK {
        value 1;
        description "No fault";
      }
      enum UNKNOWN {
        value 2;
        description "Unknown error";
      }
      enum ECOMM {
        value 3;
        description "Communication error";
      }
      enum ECFG {
        value 4;
        description "Configuration error";
      }
      enum ECOMPAT {
        value 5;
        description "Compatibility error";
      }
      enum EHW {
        value 6;
        description "Hardware error";
      }
      enum EPOWER {
        description "Power error";
      }
      enum ELPC {
        description "lpc bus error";
      }
    }
    description "Code describing cause of fault";
  }

  typedef fault-value {
    type uint32;
    description "Failt value.";
  }

  typedef input-power-type {
    type enumeration {
      enum UNKNOWN {
        value 1;
        description "Unknown";
      }
      enum AC {
        value 2;
        description "Alternating current";
      }
      enum DC {
        value 3;
        description "Direct current";
      }
    }
    description "Input current";
  }

  typedef fan-airflow-type {
    type enumeration {
      enum UNKNOWN {
        value 1;
        description "Unknown";
      }
      enum NORMAL {
        value 2;
        description "Normal airflow";
      }
      enum REVERSE {
        value 3;
        description "Reverse airflow";
      }
      enum NOT-APPLICABLE {
        value 4;
        description "airflow type not applicable";
      }
    }
    description "Fan airflow type";
  }

  typedef fan-speed-type {
    type uint16;
    units "RPM";
    description "Fan speed, in RPM";
  }

  typedef temperature-type {
    type int16;
    units "C";
    description "Temperature, in degrees C";
  }

  typedef power-usage-type {
    type uint32;
    units "mW";
    description "Power consumption, in mW";
  }

  typedef fault-severity {
    type enumeration {
      enum "cleared" {
        value 1;
      }
      enum "indeterminate" {
        value 2;
      }
      enum "critical" {
        value 3;
      }
      enum "major" {
        value 4;
      }
      enum "minor" {
        value 5;
      }
      enum "warning" {
        value 6;
      }
    }
    description
      "ITU defined severity values.";
  }

  typedef power-measurement-type {

    type enumeration {
      enum OMA {
        value 1;
        description "Optical Modulation Amplitude";
      }
      enum average {
        value 2;
        description "Average Power";
      }
    }
    description "Power measurement type";
  }

  typedef media-status {

    type enumeration {
      enum normal-status {
        value 1;
        description "Normal state, not crossed any threshold values";
      }

      enum high-alarm {
        value 2;
        description "High alarm state";
      }

      enum low-alarm {
        value 3;
        description "Low alarm state";
      }

      enum high-warning {
        value 4;
        description "High warning state";
      }

      enum low-warning {
        value 5;
        description "Low warning state";
      }
    }
    description "Media monitor status";
  }

  typedef media-support-status {

     type enumeration {
       enum not-supported {
         value 1;
         description "Media type is not supported in front panel port.";
       }

       enum not-supported-disabled {
         value 2;
         description "Media type is not supported in front panel port and its not enabled.";
       }
     }
     description "Front panel port Media type support status.";
  }

  typedef qsa-adapter {
    type enumeration {
      enum UNKNOWN {
        value 1;
        description "QSA type/status is unknown";
      }
      enum NO-QSA {
        value 2;
        description "No QSA is connected";
      }
      enum QSA {
        value 3;
        description "QSA is connected";
      }
      enum QSA28 {
        value 4;
        description "QSA28 is connected";
      }
    }
    description "Type of QSA adapter connected";
  }

  typedef ext_spec_compliance_code {
    type enumeration {
      enum UNKNOWN {
        value 1;
        description "Unkown";
      }
      enum 25GBASE-CR-CA-S {
        value 2;
        description "CA-S type for 25G";
      }
      enum 25GBASE-CR-CA-N {
        value 3;
        description "CA-N type for 25G";
      }
      enum 25GBASE-CR-CA-L {
        value 4;
        description "CA-L type for 25G";
      }
      enum NOT-APPLICABLE {
        value 5;
        description "This type is not applicable for given media";
      }
    }
    description "Used to specify certain special fields based on SFF-8024: 4.4";
  }

  typedef media-cable-type {
    type enumeration {
      enum UNKNOWN {
        value 1;
        description "Cable type is unknown";
      }
      enum FIBER {
        value 2;
        description "Cable is fiber cable";
      }
      enum DAC {
        value 3;
        description "Directly attached copper";
      }
      enum AOC {
        value 4;
        description "Active optical cable";
      }
      enum ACC {
        value 5;
        description "Active copper cable";
      }
      enum RJ45 {
        value 6;
        description "RJ45 cable";
      }
    }
    description "High level type of cable of the inserted media";
  }

  typedef media-connector-type {
    type enumeration {
      enum UNKNOWN {
        value 1;
        description "Connector type is unknown";
      }
      enum LC {
        value 2;
        description "LC: Lucent connector. Commonly used for optics";
      }
      enum MU {
        value 3;
        description "MU connector type";
      }
      enum OPTICAL-PIGTAIL {
        value 4;
        description "Optical pigtail type";
      }
      enum MPO-1X12 {
        value 5;
        description "MPO connector 1x12";
      }
      enum MPO-2X16 {
        value 6;
        description "MPO connector 2x16";
      }
      enum COPPER-PIGTAIL {
        value 7;
        description "Copper pigtail. Commonly used for DACs";
      }
      enum RJ45 {
        value 8;
        description "RJ45 connector";
      }
      enum NON-SEPARABLE {
        value 9;
        description "Cable is fixed to transceiver. Used for AOCs and DACs";
      }
      enum MXC-2X16 {
        value 10;
        description "MXC 2x16 connector";
      }
      enum CS {
        value 11;
        description "CS connector";
      }
      enum BACKPLANE {
        value 12;
        description "Backplane connector";
      }

    }
    description "The connector type of the inserted media";
  }

  typedef media-interface {

     type enumeration {

       enum UNKNOWN {
         value 1;
         description "Unknown media interface type";
       }
       enum BASE-T {
         value 2;
         description "BASE-T; commonly used for RJ45";
       }
       enum FX {
         value 3;
         description "FX";
       }
       enum BIDI {
         value 4;
         description "BIDI; bidirectional";
       }
       enum BX10 {
         value 5;
         description "BX10; BX with 10km distance";
       }
       enum BX40 {
         value 6;
         description "BX40; BX with 40km distance";
       }
       enum BX80 {
         value 7;
         description "BX80; BX with 80km distance";
       }
       enum CR {
         value 8;
         description "CR; copper reach. Used for DAC (directlt attached copper). Protocol is purely electrical";
       }
       enum SR {
         value 9;
         description "SR; short reach optics";
       }
       enum LR {
         value 10;
         description "LR; long reach optics";
       }
       enum ER {
         value 11;
         description "ER";
       }
       enum ZR {
         value 12;
         description "ZR";
       }
       enum USR {
         value 13;
         description "USR; ultra short reach optics";
       }
       enum CWDM {
         value 14;
         description "CWDM; coarse wavelength division multiplexing optics";
       }
       enum DWDM {
         value 15;
         description "CWDM; dense wavelength division multiplexing optics";
       }
       enum SWDM {
         value 16;
         description "SWDM; short wavelength division multiplexing optics";
       }
       enum SX {
         value 17;
         description "SX; short reach optics";
       }
       enum LX {
         value 18;
         description "LX; long reach optics";
       }
       enum ZX {
         value 19;
         description "ZR; extended reach optics";
       }
       enum LM {
         value 20;
         description "LM";
       }
       enum LRM {
         value 21;
         description "LRM";
       }
       enum PSM {
         value 22;
         description "PSM";
       }
       enum PLR {
         value 23;
         description "PLR";
       }
       enum SM {
         value 24;
         description "SM";
       }
       enum SW {
         value 25;
         description "Sw";
       }
       enum LW {
         value 26;
         description "LW";
       }
       enum RJ45 {
         value 27;
         description "RJ45";
       }
       enum ELECTRICAL-LOOPBACK {
         value 28;
         description "Electrical loopback";
       }
       enum BACKPLANE {
         value 29;
         description "Backplane type";
       }
       enum CX {
         value 30;
         description "CX";
       }
       enum PX {
         value 31;
         description "PX";
       }
       enum ESR {
         value 32;
         description "ESR";
       }
    }
    description "Interface type of the lineside of the media ";
  }

  typedef media-interface-qualifier {

     type enumeration {

       enum UNKNOWN {
         value 1;
         description "Unknown media interface qualifier";
       }
       enum NO-QUALIFIER {
         value 2;
         description "All info needed is provided by media-interface";
       }
       enum IR {
         value 3;
         description "IR";
       }
       enum LR {
         value 4;
         description "LR";
       }
       enum 1490NM {
         value 5;
         description "1490nanometer wavelength";
       }
       enum 30M {
         value 6;
         description "30meter reach";
       }
       enum UP {
         value 7;
         description "UP";
       }
       enum DOWN {
         value 8;
         description "DOWN";
       }
       enum ACC {
         value 9;
         description "Active copper cable";
       }
       enum NOF {
         value 10;
         description "No FEC";
       }
       enum TUNABLE {
         value 11;
         description "Tunable";
       }
       enum LITE {
         value 12;
         description "Lite";
       }
       enum FIXED {
         value 13;
         description "Fixed type media";
       }
       enum AOC {
         value 14;
         description "Active optical cable";
       }
    }
    description "Interface qualifier type of the lineside of the media. This provides additional info about the media interface ";
  }

  typedef port-type {
    type enumeration {
      enum PLUGGABLE {
        value 1;
        description "Pluggable port type";
      }
      enum FIXED {
        value 2;
        description "Fixed port type";
      }
      enum BACKPLANE {
        value 3;
        description "Backplane port type";
      }
    }
    description "Port Type";
  }

  typedef media-category {
    type enumeration {
      enum SFP {
        value 1;
        description "SFP media category";
      }
      enum SFP-PLUS {
        value 2;
        description "SFP+ media category";
      }
      enum QSFP {
        value 3;
        description "QSFP media category";
      }
      enum QSFP-PLUS {
        value 4;
        description "QSFP+ media category";
      }
      enum QSFP28 {
        value 5;
        description "QSFP28 media category";
      }
      enum SFP28 {
        value 6;
        description "SFP28 media category";
      }
      enum CXP {
        value 7;
        description "CXP media category";
      }
      enum CXP28 {
        value 8;
        description "CXP28 media category";
      }
      enum QSFP-DD {
        value 9;
        description "QSFP-DD media category";
      }
      enum DEPOP-QSFP28 {
        value 10;
        description "Depopulated QSFP28 media category";
      }
      enum FIXED {
        value 11;
        description "Fixed media category";
      }
    }
    description "Media category";
  }

  typedef media-type {
      type enumeration {
          enum AR_POPTICS_NOTPRESENT {
              value 1;
              description "Pluggable optics not present";
          }
          enum AR_POPTICS_UNKNOWN {
              value 2;
              description "Pluggable optics unknown";
          }
          enum AR_POPTICS_NOTSUPPORTED {
              value 3;
              description "Pluggable optics not supported";
          }
          enum AR_SFPPLUS_10GBASE_USR {
              value 4;
              description "Pluggable optics SFPPLUS_10GBASE_USR";
          }
          enum AR_SFPPLUS_10GBASE_SR {
              value 5;
              description "Pluggable optics SFPPLUS_10GBASE_SR";
          }
          enum AR_SFPPLUS_10GBASE_LR {
              value 6;
              description "Pluggable optics SFPPLUS_10GBASE_LR";
          }
          enum AR_SFPPLUS_10GBASE_ER {
              value 7;
              description "Pluggable optics SFPPLUS_10GBASE_ER";
          }
          enum AR_SFPPLUS_10GBASE_ZR {
              value 8;
              description "Pluggable optics SFPPLUS_10GBASE_ZR";
          }
          enum AR_SFPPLUS_10GBASE_CX4 {
              value 9;
              description "Pluggable optics SFPPLUS_10GBASE_CX4";
          }
          enum AR_SFPPLUS_10GBASE_LRM {
              value 10;
              description "Pluggable optics SFPPLUS_10GBASE_LRM";
          }
          enum AR_SFPPLUS_10GBASE_T {
              value 11;
              description "Pluggable optics AR_SFPPLUS_10GBASE_T";
          }
          enum AR_SFPPLUS_10GBASE_CUHALFM {
              value 12;
              description "Pluggable optics SFPPLUS_10GBASE_CUHALFM";
          }
          enum AR_SFPPLUS_10GBASE_CU1M {
              value 13;
              description "Pluggable optics SFPPLUS_10GBASE_CU1M";
          }
          enum AR_SFPPLUS_10GBASE_CU2M {
              value 14;
              description "Pluggable optics SFPPLUS_10GBASE_CU2M";
          }
          enum AR_SFPPLUS_10GBASE_CU3M {
              value 15;
              description "Pluggable optics SFPPLUS_10GBASE_CU3M";
          }
          enum AR_SFPPLUS_10GBASE_CU5M {
              value 16;
              description "Pluggable optics SFPPLUS_10GBASE_CU5M";
          }
          enum AR_SFPPLUS_10GBASE_CU7M {
              value 17;
              description "Pluggable optics SFPPLUS_10GBASE_CU7M";
          }
          enum AR_SFPPLUS_10GBASE_CU10M {
              value 18;
              description "Pluggable optics SFPPLUS_10GBASE_CU10M";
          }
          enum AR_SFPPLUS_10GBASE_ACU7M {
              value 19;
              description "Pluggable optics SFPPLUS_10GBASE_ACU7M";
          }
          enum AR_SFPPLUS_10GBASE_ACU10M {
              value 20;
              description "Pluggable optics SFPPLUS_10GBASE_ACU10M";
          }
          enum AR_SFPPLUS_10GBASE_ACU15M {
              value 21;
              description "Pluggable optics SFPPLUS_10GBASE_ACU15M";
          }
          enum AR_SFPPLUS_10GBASE_DWDM {
              value 22;
              description "Pluggable optics SFPPLUS_10GBASE_DWDM";
          }
          enum AR_SFPPLUS_10GBASE_DWDM_40KM {
              value 23;
              description "Pluggable optics SFPPLUS_10GBASE_DWDM_40KM";
          }
          enum AR_SFPPLUS_10GBASE_DWDM_80KM {
              value 24;
              description "Pluggable optics SFPPLUS_10GBASE_DWDM_80KM";
          }
          enum AR_QSFP_40GBASE_SR4 {
              value 25;
              description "Pluggable optics QSFP_40GBASE_SR4";
          }
          enum AR_QSFP_40GBASE_SR4_EXT {
              value 26;
              description "Pluggable optics QSFP_40GBASE_SR4_EXT";
          }
          enum AR_QSFP_40GBASE_LR4 {
              value 27;
              description "Pluggable optics QSFP_40GBASE_LR4";
          }
          enum AR_QSFP_40GBASE_LM4 {
              value 28;
              description "Pluggable optics QSFP_40GBASE_LM4";
          }
          enum AR_QSFP_40GBASE_PSM4_LR {
              value 29;
              description "Pluggable optics QSFP_40GBASE_PSM4_LR";
          }
          enum AR_QSFP_40GBASE_PSM4_1490NM {
              value 30;
              description "Pluggable optics QSFP_40GBASE_PSM4_1490NM";
          }
          enum AR_QSFP_40GBASE_PSM4_1490NM_1M {
              value 31;
              description "Pluggable optics QSFP_40GBASE_PSM4_1490NM_1M";
          }
          enum AR_QSFP_40GBASE_PSM4_1490NM_3M {
              value 32;
              description "Pluggable optics QSFP_40GBASE_PSM4_1490NM_3M";
          }
          enum AR_QSFP_40GBASE_PSM4_1490NM_5M {
              value 33;
              description "Pluggable optics QSFP_40GBASE_PSM4_1490NM_5M";
          }
          enum AR_4x1_1000BASE_T {
              value 34;
              description "Pluggable optics 4x1_1000BASE_T";
          }
          enum AR_QSFP_40GBASE_CR4_HAL_M {
              value 35;
              status deprecated;
              description "Pluggable optics QSFP_40GBASE_CR4_HAL_M";
          }
          enum AR_QSFP_40GBASE_CR4_1M {
              value 36;
              description "Pluggable optics QSFP_40GBASE_CR4_1M";
          }
          enum AR_QSFP_40GBASE_CR4_2M {
              value 37;
              description "Pluggable optics QSFP_40GBASE_CR4_2M";
          }
          enum AR_QSFP_40GBASE_CR4_3M {
              value 38;
              description "Pluggable optics QSFP_40GBASE_CR4_3M";
          }
          enum AR_QSFP_40GBASE_CR4_5M {
              value 39;
              description "Pluggable optics QSFP_40GBASE_CR4_5M";
          }
          enum AR_QSFP_40GBASE_CR4_7M {
              value 40;
              description "Pluggable optics QSFP_40GBASE_CR4_7M";
          }
          enum AR_QSFP_40GBASE_CR4_10M {
              value 41;
              description "Pluggable optics QSFP_40GBASE_CR4_10M";
          }
          enum AR_QSFP_40GBASE_CR4_50M {
              value 42;
              description "Pluggable optics QSFP_40GBASE_CR4_50M";
          }
          enum AR_QSFP_40GBASE_CR4 {
              value 43;
              description "Pluggable optics QSFP_40GBASE_CR4";
          }
          enum AR_4x10_10GBASE_CR1_HAL_M {
              value 44;
              status deprecated;
              description "Pluggable optics 4x10_10GBASE_CR1_HAL_M";
          }
          enum AR_4x10_10GBASE_CR1_1M {
              value 45;
              description "Pluggable optics 4x10_10GBASE_CR1_1M";
          }
          enum AR_4x10_10GBASE_CR1_3M {
              value 46;
              description "Pluggable optics 4x10_10GBASE_CR1_3M";
          }
          enum AR_4x10_10GBASE_CR1_5M {
              value 47;
              description "Pluggable optics 4x10_10GBASE_CR1_5M";
          }
          enum AR_4x10_10GBASE_CR1_7M {
              value 48;
              description "Pluggable optics 4x10_10GBASE_CR1_7M";
          }
          enum AR_SFPPLUS_FC_8GBASE_SR {
              value 49;
              description "Pluggable optics SFPPLUS_FC_8GBASE_SR";
          }
          enum AR_SFPPLUS_FC_8GBASE_IR {
              value 50;
              description "Pluggable optics SFPPLUS_FC_8GBASE_IR";
          }
          enum AR_SFPPLUS_FC_8GBASE_MR {
              value 51;
              description "Pluggable optics SFPPLUS_FC_8GBASE_MR";
          }
          enum AR_SFPPLUS_FC_8GBASE_LR {
              value 52;
              description "Pluggable optics SFPPLUS_FC_8GBASE_LR";
          }
          enum SFP_SX {
              value 53;
              description "Pluggable optics SFP_SX";
          }
          enum SFP_LX {
              value 54;
              description "Pluggable optics SFP_LX";
          }
          enum SFP_ZX {
              value 55;
              description "Pluggable optics SFP_ZX";
          }
          enum SFP_CX {
              value 56;
              description "Pluggable optics SFP_CX";
          }
          enum SFP_DX {
              value 57;
              description "Pluggable optics SFP_DX";
          }
          enum SFP_T {
              value 58;
              description "Pluggable optics SFP_T";
          }
          enum SFP_FX {
              value 59;
              description "Pluggable optics SFP_FX";
          }
          enum SFP_CWDM {
              value 60;
              description "Pluggable optics SFP_CWDM";
          }
          enum SFP_IR1 {
              value 61;
              description "Pluggable optics SFP_IR1";
          }
          enum SFP_LR1 {
              value 62;
              description "Pluggable optics SFP_LR1";
          }
          enum SFP_LR2 {
              value 63;
              description "Pluggable optics SFP_LR2";
          }
          enum SFP_BX10 {
              value 64;
              description "Pluggable optics SFP_BX10";
          }
          enum SFP_PX {
              value 65;
              description "Pluggable optics SFP_PX";
          }
          enum 4x_10GBASE_SR_AOCXXM {
              value 66;
              description "Pluggable optics 4x10GBASE-SR-AOCXXM";
          }
          enum QSFP_40GBASE_SM4 {
              value 67;
              description "Pluggable optics QSFP_40GBASE_SM4";
          }
          enum QSFP_40GBASE_ER4 {
              value 68;
              description "Pluggable optics QSFP_40GBASE_ER4";
          }
          enum QSFP_4x10_10GBASE_CR1_2M {
              value 69;
              description "Pluggable optics QSFP_4x10_10GBASE_CR1_2M";
          }
          enum SFPPLUS_10GBASE_ZR_TUNABLE {
              value 70;
              description "Pluggable optics SFPPLUS_10GBASE_ZR_TUNABLE";
          }
          enum AR_QSFP28_100GBASE_SR4 {
              value 71;
              description "Pluggable optics AR_QSFP28_100GBASE_SR4";
          }
          enum AR_QSFP28_100GBASE_LR4 {
              value 72;
              description "Pluggable optics AR_QSFP28_100GBASE_LR4";
          }
          enum AR_QSFP28_100GBASE_CWDM4 {
              value 73;
              description "Pluggable optics AR_QSFP28_100GBASE_CWDM4";
          }
          enum AR_QSFP28_100GBASE_PSM4_IR {
              value 74;
              description "Pluggable optics AR_QSFP28_100GBASE_PSM4_IR";
          }
          enum AR_QSFP28_100GBASE_CR4 {
              value 75;
              description "Pluggable optics AR_QSFP28_100GBASE_CR4";
          }
          enum AR_QSFP28_100GBASE_AOC {
              value 76;
              description "Pluggable optics AR_QSFP28_100GBASE_AOC";
          }
          enum AR_QSFP28_100GBASE_CR4_HAL_M {
              value 77;
              status deprecated;
              description "Pluggable optics AR_QSFP28_100GBASE_CR4_HALFM";
          }
          enum AR_QSFP28_100GBASE_CR4_1M {
              value 78;
              description "Pluggable optics AR_QSFP28_100GBASE_CR4_1M";
          }
          enum AR_QSFP28_100GBASE_CR4_2M {
              value 79;
              description "Pluggable optics AR_QSFP28_100GBASE_CR4_2M";
          }
          enum AR_QSFP28_100GBASE_CR4_3M {
              value 80;
              description "Pluggable optics AR_QSFP28_100GBASE_CR4_3M";
          }
          enum AR_QSFP28_100GBASE_CR4_4M {
              value 81;
              description "Pluggable optics AR_QSFP28_100GBASE_CR4_4M";
          }
          enum AR_QSFP28_100GBASE_CR4_5M {
              value 82;
              description "Pluggable optics AR_QSFP28_100GBASE_CR4_5M";
          }
          enum QSFP28_100GBASE_CR4_7M {
              value 83;
              description "Pluggable optics QSFP28_100GBASE_CR4_7M";
          }
          enum QSFP28_100GBASE_CR4_10M {
              value 84;
              description "Pluggable optics QSFP28_100GBASE_CR4_10M";
          }
          enum QSFP28_100GBASE_CR4_50M {
              value 85;
              description "Pluggable optics QSFP28_100GBASE_CR4_50M";
          }
          enum 4X25_25GBASE_CR1_HALF_M {
              value 86;
              status deprecated;
              description "Pluggable optics 4X25_25GBASE_CR1_HALF_M";
          }
          enum 4X25_25GBASE_CR1_1M {
              value 87;
              description "Pluggable optics 4X25_25GBASE_CR1_1M";
          }
          enum 4X25_25GBASE_CR1_2M {
              value 88;
              description "Pluggable optics 4X25_25GBASE_CR1_2M";
          }
          enum 4X25_25GBASE_CR1_3M {
              value 89;
              description "Pluggable optics 4X25_25GBASE_CR1_3M";
          }
          enum 4X25_25GBASE_CR1_4M {
              value 90;
              description "Pluggable optics 4X25_25GBASE_CR1_4M";
          }
          enum 4X25_25GBASE_CR1 {
              value 91;
              description "Pluggable optics 4X25_25GBASE_CR1";
          }
          enum 2X50_50GBASE_CR2_HALF_M {
              value 92;
              status deprecated;
              description "Pluggable optics 2X50_50GBASE_CR2_HALF_M";
          }
          enum 2X50_50GBASE_CR2_1M {
              value 93;
              description "Pluggable optics 2X50_50GBASE_CR2_1M";
          }
          enum 2X50_50GBASE_CR2_2M {
              value 94;
              description "Pluggable optics 2X50_50GBASE_CR2_2M";
          }
          enum 2X50_50GBASE_CR2_3M {
              value 95;
              description "Pluggable optics 2X50_50GBASE_CR2_3M";
          }
          enum 2X50_50GBASE_CR2_4M {
              value 96;
              description "Pluggable optics 2X50_50GBASE_CR2_4M";
          }
          enum 2X50_50GBASE_CR2 {
              value 97;
              description "Pluggable optics 2X50_50GBASE_CR2";
          }
          enum SFP28_25GBASE_CR1 {
              value 98;
              description "Pluggable optics SFP28_25GBASE_CR1";
          }
          enum SFP28_25GBASE_CR1_HALF_M {
              value 99;
              status deprecated;
              description "Pluggable optics SFP28_25GBASE_CR1_HALF_M";
          }
          enum SFP28_25GBASE_CR1_1M {
              value 100;
              description "Pluggable optics SFP28_25GBASE_CR1_1M";
          }
          enum SFP28_25GBASE_CR1_2M {
              value 101;
              description "Pluggable optics SFP28_25GBASE_CR1_2M";
          }
          enum SFP28_25GBASE_CR1_3M {
              value 102;
              description "Pluggable optics SFP28_25GBASE_CR1_3M";
          }
          enum QSFPPLUS_50GBASE_CR2 {
              value 103;
              description "Pluggable optics QSFPPLUS_50GBASE_CR2";
          }
          enum QSFPPLUS_50GBASE_CR2_1M {
              value 104;
              description "Pluggable optics QSFPPLUS_50GBASE_CR2_1M";
          }
          enum QSFPPLUS_50GBASE_CR2_2M {
              value 105;
              description "Pluggable optics QSFPPLUS_50GBASE_CR2_2M";
          }
          enum QSFPPLUS_50GBASE_CR2_3M {
              value 106;
              description "Pluggable optics QSFPPLUS_50GBASE_CR2_3M";
          }
          enum QSFP_40GBASE_BIDI {
              value 107;
              description "Pluggable optics QSFP_40GBASE_BIDI";
          }
          enum QSFP_40GBASE_AOC {
              value 108;
              description "Pluggable optics QSFP_40GBASE_AOC";
          }
          enum QSFP28_100GBASE_LR4_LITE {
              value 109;
              description "Pluggable optics QSFP28_100GBASE_LR4_LITE";
          }
          enum QSFP28_100GBASE_ER4 {
              value 110;
              description "Pluggable optics QSFP28_100GBASE_ER4";
          }
          enum QSFP28_100GBASE_ACC {
              value 111;
              description "Pluggable optics QSFP28_100GBASE_ACC ";
          }
          enum SFP28_25GBASE_SR {
              value 112;
              description "Pluggable optics SFP28_25GBASE_SR";
          }
          enum SFPPLUS_10GBASE_SR_AOCXXM {
              value 113;
              description "Pluggable optics SFPPLUS_10GBASE_SR_AOCXXM";
          }
          enum SFP_BX10_UP {
              value 114;
              description "Pluggable optics SFP_BX10_UP";
          }
          enum SFP_BX10_DOWN {
              value 115;
              description "Pluggable optics SFP_BX10_DOWN";
          }
          enum SFP_BX40_UP {
              value 116;
              description "Pluggable optics SFP_BX40_UP";
          }
          enum SFP_BX40_DOWN {
              value 117;
              description "Pluggable optics SFP_BX40_DOWN";
          }
          enum SFP_BX80_UP {
              value 118;
              description "Pluggable optics SFP_BX80_UP";
          }
          enum SFP_BX80_DOWN {
              value 119;
              description "Pluggable optics SFP_BX80_DOWN";
          }
          enum QSFP28_100GBASE_PSM4_PIGTAIL {
              value 120;
              description "Pluggable optics QSFP28_100GBASE_PSM4_PIGTAIL";
          }
          enum QSFP28_100GBASE_SWDM4 {
              value 121;
              description "Pluggable optics QSFP28_100GBASE_SWDM4";
          }
          enum QSFP_40GBASE_PSM4_PIGTAIL {
              value 122;
              description "Pluggable optics QSFP_40GBASE_PSM4_PIGTAIL";
          }
          enum AR_QSFP_40GBASE_CR4_HALFM {
              value 123;
              description "Pluggable optics QSFP_40GBASE_CR4_HALFM";
          }
          enum AR_4x10_10GBASE_CR1_HALFM {
              value 124;
              description "Pluggable optics 4x10_10GBASE_CR1_HALFM";
          }
          enum AR_QSFP28_100GBASE_CR4_HALFM {
              value 125;
              description "Pluggable optics AR_QSFP28_100GBASE_CR4_HALFM";
          }
          enum 4X25_25GBASE_CR1_HALFM {
              value 126;
              description "Pluggable optics 4X25_25GBASE_CR1_HALFM";
          }
          enum 2X50_50GBASE_CR2_HALFM {
              value 127;
              description "Pluggable optics 2X50_50GBASE_CR2_HALFM";
          }
          enum SFP28_25GBASE_CR1_HALFM {
              value 128;
              description "Pluggable optics SFP28_25GBASE_CR1_HALFM";
          }
          enum SFPPLUS_8GBASE_FC_SW {
              value 129;
              description "Pluggable optics SFPPLUS_8GBASE_FC_SW";
          }
          enum SFPPLUS_8GBASE_FC_LW {
              value 130;
              description "Pluggable optics SFPPLUS_8GBASE_FC_LW";
          }
          enum SFPPLUS_16GBASE_FC_SW {
              value 131;
              description "Pluggable optics SFPPLUS_16GBASE_FC_SW";
          }
          enum SFPPLUS_16GBASE_FC_LW {
              value 132;
              description "Pluggable optics SFPPLUS_16GBASE_FC_LW";
          }
          enum QSFPPLUS_64GBASE_FC_SW4 {
              value 133;
              description "Pluggable optics QSFPPLUS_64GBASE_FC_SW4";
          }
          enum QSFPPLUS_4X16_16GBASE_FC_SW {
              value 134;
              description "Pluggable optics QSFPPLUS_4X16_16GBASE_FC_SW";
          }
          enum QSFPPLUS_64GBASE_FC_LW4 {
              value 135;
              description "Pluggable optics QSFPPLUS_64GBASE_FC_LW4";
          }
          enum QSFPPLUS_4X16_16GBASE_FC_LW {
              value 136;
              description "Pluggable optics QSFPPLUS_4X16_16GBASE_FC_LW";
          }
          enum QSFP28_128GBASE_FC_SW4 {
              value 137;
              description "Pluggable optics QSFP28_128GBASE_FC_SW4";
          }
          enum QSFP28_4X32_32GBASE_FC_SW {
              value 138;
              description "Pluggable optics QSFP28_4X32_32GBASE_FC_SW";
          }
          enum QSFP28_128GBASE_FC_LW4 {
              value 139;
              description "Pluggable optics QSFP28_128GBASE_FC_LW4";
          }
          enum QSFP28_4X32_32GBASE_FC_LW {
              value 140;
              description "Pluggable optics QSFP28_4X32_32GBASE_FC_LW";
          }
          enum SFP28_32GBASE_FC_SW {
              value 141;
              description "Pluggable optics SFP28_32GBASE_FC_SW";
          }
          enum SFP28_32GBASE_FC_LW {
              value 142;
              description "Pluggable optics SFP28_32GBASE_FC_LW";
          }
          enum SFP28_25GBASE_SR_NOF {
              value 143;
              description "Pluggable optics SFP28_25GBASE_SR_NOF";
          }
          enum SFP28_25GBASE_eSR {
              value 144;
              description "Pluggable optics SFP28_25GBASE_eSR";
          }
          enum SFP28_25GBASE_LR {
              value 145;
              description "Pluggable optics SFP28_25GBASE_LR";
          }
          enum SFP28_25GBASE_LR_LITE {
              value 146;
              description "Pluggable optics SFP28_25GBASE_LR_LITE";
          }
          enum SFP28_25GBASE_SR_AOCXXM {
              value 147;
              description "Pluggable optics SFP28_25GBASE_SR_AOCXXM";
          }
          enum SFP28_25GBASE_CR1_LPBK {
              value 148;
              description "Pluggable optics SFP28_25GBASE_CR1_LPBK";
          }
          enum QSFP28-DD_200GBASE_CR4_HALFM {
              value 149;
              description "Pluggable optics QSFP28-DD_200GBASE_CR4_HALFM";
          }
          enum QSFP28-DD_200GBASE_CR4_1M {
              value 150;
              description "Pluggable optics QSFP28-DD_200GBASE_CR4_1M";
          }
          enum QSFP28-DD_200GBASE_CR4_2M {
              value 151;
              description "Pluggable optics QSFP28-DD_200GBASE_CR4_2M";
          }
          enum QSFP28-DD_200GBASE_CR4_3M {
              value 152;
              description "Pluggable optics QSFP28-DD_200GBASE_CR4_3M";
          }
          enum QSFP28-DD_200GBASE_CR4_5M {
              value 153;
              description "Pluggable optics QSFP28-DD_200GBASE_CR4_5M";
          }
          enum QSFP28-DD_200GBASE_CR4 {
              value 154;
              description "Pluggable optics QSFP28-DD_200GBASE_CR4";
          }
          enum "QSFP28-DD_200GBASE_CR4_1_HALFM" {
              value 155;
              description "Pluggable optics QSFP28-DD_200GBASE_CR4_1_HALFM";
          }
          enum QSFP28-DD_200GBASE_CR4_2_HALFM {
              value 156;
              description "Pluggable optics QSFP28-DD_200GBASE_CR4_2_HALFM";
          }
          enum QSFP28-DD_2x100GBASE_CR4_1M {
              value 157;
              description "Pluggable optics QSFP28-DD_2x100GBASE_CR4_1M";
          }
          enum QSFP28-DD_2x100GBASE_CR4_2M {
              value 158;
              description "Pluggable optics QSFP28-DD_2x100GBASE_CR4_2M";
          }
          enum QSFP28-DD_2x100GBASE_CR4_3M {
              value 159;
              description "Pluggable optics QSFP28-DD_2x100GBASE_CR4_3M";
          }
          enum QSFP28-DD_8x25GBASE_CR4_1M {
              value 160;
              description "Pluggable optics QSFP28-DD_8x25GBASE_CR4_1M";
          }
          enum QSFP28-DD_8x25GBASE_CR4_2M {
              value 161;
              description "Pluggable optics QSFP28-DD_8x25GBASE_CR4_2M";
          }
          enum QSFP28-DD_8x25GBASE_CR4_3M {
              value 162;
              description "Pluggable optics QSFP28-DD_8x25GBASE_CR4_3M";
          }
          enum QSFP28-DD_200GBASE_CR4_LPBK {
              value 163;
              description "Pluggable optics QSFP28-DD_200GBASE_CR4_LPBK";
          }
          enum SFPPLUS_10GBASE_CR_1_HALFM {
              value 164;
              description "Pluggable optics SFPPLUS_10GBASE_CR_1.5M";
          }
          enum SFPPLUS_10GBASE_CR_2_HALFM {
              value 165;
              description "Pluggable optics SFPPLUS_10GBASE_CR_2.5M";
          }
          enum SFPPLUS_10GBASE_CR_1M {
              value 166;
              description "Pluggable optics SFPPLUS_10GBASE_CR_1M";
          }
          enum SFPPLUS_10GBASE_CR_2M {
              value 167;
              description "Pluggable optics SFPPLUS_10GBASE_CR_2M";
          }
          enum SFPPLUS_10GBASE_CR_3M {
              value 168;
              description "Pluggable optics SFPPLUS_10GBASE_CR_3M";
          }
          enum SFPPLUS_10GBASE_CR_4M {
              value 169;
              description "Pluggable optics SFPPLUS_10GBASE_CR_4M";
          }
          enum SFPPLUS_10GBASE_CR_5M {
              value 170;
              description "Pluggable optics SFPPLUS_10GBASE_CR_5M";
          }
          enum QSFP28-DD_200GBASE_SR4_HALFM {
              value 171;
              description "Pluggable optics QSFP28-DD_200GBASE_SR4_HALFM";
          }
          enum QSFP28-DD_200GBASE_SR4_1M {
              value 172;
              description "Pluggable optics QSFP28-DD_200GBASE_SR4_1M";
          }
          enum QSFP28-DD_200GBASE_SR4_2M {
              value 173;
              description "Pluggable optics QSFP28-DD_200GBASE_SR4_2M";
          }
          enum QSFP28-DD_200GBASE_SR4_3M {
              value 174;
              description "Pluggable optics QSFP28-DD_200GBASE_SR4_3M";
          }
          enum QSFP28-DD_200GBASE_SR4_5M {
              value 175;
              description "Pluggable optics QSFP28-DD_200GBASE_SR4_5M";
          }
          enum QSFP28-DD_200GBASE_SR4 {
              value 176;
              description "Pluggable optics QSFP28-DD_200GBASE_SR4";
          }
          enum QSFP28-DD_200GBASE_SR4_1_HALFM {
              value 177;
              description "Pluggable optics QSFP28-DD_200GBASE_SR4_1_HALFM";
          }
          enum QSFP28-DD_200GBASE_SR4_2_HALFM {
              value 178;
              description "Pluggable optics QSFP28-DD_200GBASE_SR4_2_HALFM";
          }
          enum 1GBASE_COPPER {
              value 179;
              description "Fixed copper port 1GBASE_COPPER";
          }
          enum 10GBASE_COPPER {
              value 180;
              description "Fixed copper port 10GBASE_COPPER";
          }
          enum 25GBASE_BACKPLANE {
              value 181;
              description "Fixed backplane port 25GBASE_BACKPLANE";
          }

          enum SFPPLUS_10GBASE_SR_AOC1M {
              value 182;
              description "Pluggable optics SFPPLUS_10GBASE_SR_AOC1M";
          }

          enum SFPPLUS_10GBASE_SR_AOC3M {
              value 183;
              description "Pluggable optics SFPPLUS_10GBASE_SR_AOC3M";
          }

          enum SFPPLUS_10GBASE_SR_AOC5M {
              value 184;
              description "Pluggable optics SFPPLUS_10GBASE_SR_AOC5M";
          }

          enum SFPPLUS_10GBASE_SR_AOC10M {
              value 185;
              description "Pluggable optics SFPPLUS_10GBASE_SR_AOC10M";
          }

          enum QSFPPLUS_4X10_10GBASE_SR_AOC10M {
              value 186;
              description "Pluggable optics QSFPPLUS_4X10_10GBASE_SR_AOC10M";
          }

          enum QSFPPLUS_40GBASE_SR_AOC3M {
              value 187;
              description "Pluggable optics QSFPPLUS_40GBASE_SR_AOC3M";
          }

          enum QSFPPLUS_40GBASE_SR_AOC5M {
              value 188;
              description "Pluggable optics QSFPPLUS_40GBASE_SR_AOC5M";
          }

          enum QSFPPLUS_40GBASE_SR_AOC7M {
              value 189;
              description "Pluggable optics QSFPPLUS_40GBASE_SR_AOC7M";
          }

          enum QSFPPLUS_40GBASE_SR_AOC10M {
              value 190;
              description "Pluggable optics QSFPPLUS_40GBASE_SR_AOC10M";
          }

          enum QSFP28-DD_2x100GBASE_CR4 {
              value 191;
              description "Pluggable 2x breakout optics QSFP28-DD_2x100GBASE_CR4 with length unspecified ";
          }

          enum QSFP28-DD_2x100GBASE_CR4_1_HALFM {
              value 192;
              description "Pluggable breakout optics QSFP28-DD_2x100GBASE_CR4_1_HALFM";
          }

          enum QSFP28-DD_8x25GBASE_CR1 {
              value 193;
              description "Pluggable 8x breakout optics QSFP28-DD_8x25GBASE_CR1 with length unspecified";
          }

          enum QSFP28-DD_8x25GBASE_CR4_1_HALFM {
              value 194;
              description "Pluggable optics QSFP28-DD_8x25GBASE_CR4_1_HALFM";
          }

          enum QSFP28-DD_8x25GBASE_2SR4_AOC {
              value 195;
              description "Pluggable 8x breakout optics QSFP28-DD_8x25GBASE_2SR4_AOC with length unspecified ";
          }

          enum QSFP28-DD_200GBASE_2SR4_AOC {
              value 196;
              description "Pluggable optics QSFP28-DD_200GBASE_2SR4_AOC with length unspecified ";
          }

          enum QSFP28-DD_2x100GBASE_SR4_AOC {
              value 197;
              description "Pluggable 2x breakout optics QSFP28-DD_2x100GBASE_SR4_AOC with length unspecified ";
          }

          enum QSFP28-DD_200GBASE_CWDM4 {
              value 198;
              description "Pluggable optics QSFP28-DD_200GBASE_CWDM4";
          }

          enum QSFP28-DD_200GBASE_PSM4_IR {
              value 199;
              description "Pluggable optics QSFP28-DD_200GBASE_PSM4_IR";
          }

          enum QSFP28_4X25GBASE_SR_AOC_XXM {
              value 200;
              description "Pluggable 4x breakout optics with any length";
          }

          enum QSFP28_100GBASE_BIDI {
              value 201;
              description "Pluggable optics QSFP28_100GBASE_BIDI";
          }

          enum QSFP28_100GBASE_ESR4 {
              value 202;
              description "Pluggable optics QSFP28_100GBASE_ESR4";
          }

          enum QSFP28_100GBASE_SR4_NOF {
              value 203;
              description "Pluggable optics QSFP28_100GBASE_SR4_NOF (No FEC)";
          }

          enum SFP_PLUS_10GBASE_BX10_UP {
              value 204;
              description "Pluggable optics SFP_PLUS_10GBASE_BX10_UP";
          }

          enum SFP_PLUS_10GBASE_BX10_DOWN {
              value 205;
              description "Pluggable optics SFP_PLUS_10GBASE_BX10_DOWN";
          }

          enum SFP_PLUS_10GBASE_BX40_UP {
              value 206;
              description "Pluggable optics SFP_PLUS_10GBASE_BX40_DOWN";
          }

          enum SFP_PLUS_10GBASE_BX40_DOWN {
              value 207;
              description "Pluggable optics SFP_PLUS_10GBASE_BX40_DOWN";
          }

          enum QSFPPLUS_40GBASE_BIDI {
              value 208;
              description "Pluggable optics QSFPPLUS_40GBASE_BIDI";
          }

          enum QSFP28_100GBASE_DWDM2 {
              value 209;
              description "Pluggable optics QSFP28_100GBASE_DWDM2";
          }

          enum QSFP28_100GBASE_ER4_LITE {
              value 210;
              description "Pluggable optics QSFP28_100GBASE_ER4_LITE";
          }

          enum QSFPPLUS_40GBASE_SR4_AOC1M {
              value 211;
              description "Pluggable optics QSFPPLUS_40GBASE_SR4_AOC1M";
          }

          enum SFP28_25GBASE_CR1_5M {
              value 212;
              description "Pluggable optics SFP28_25GBASE_CR1_5M";
          }
      }
      description "Media type";
  }

  typedef reboot-type {
    type enumeration {
      enum WARM {
        value 1;
        description "Warm reboot";
      }
      enum COLD {
        value 2;
        description "Cold reboot";
      }
    }
    description "define reboot type";
  }

  typedef unit-down-reason {
    type enumeration {
      enum "version-mismatch" {
        value 1;
      }
      enum "type-mismatch" {
        value 2;
      }
      enum "admin-down" {
        value 3;
      }
      enum "unlicensed" {
        value 4;
      }
      enum "user-triggered" {
        value 5;
      }
      enum "software-triggered" {
        value 6;
      }
      enum "unit-crashed" {
        value 7;
      }
      enum "unknown" {
        value 8;
      }
    }
    description
      "Indicates reason for unit down.";
  }

  // PAS notify grouping

  grouping pas_notify {

    leaf status {
      type boolean;
      config false;
      description "PAS status";
    }
    description "Attributes of pas notify";
  }

  // Platform fault grouping

  grouping pas_fault {

    leaf fault-type {
      type fault-type;
      config false;
      description " platform fault";
    }
    description "Attributes of PAS fault notify";
  }


  // EEPROM grouping - Everything there is to know about a
  //                   chassis' or entity's EEPROM

  grouping eeprom {

    leaf vendor-name {
      type string;
      config false;
      // Qualifiers: observed, realtime
      // Dependencies: Valid only if entity is present
      // Persistent: N/A
      // Notification: no
      description "Entity vendor name";
    }

    leaf product-name {
      type string;
      config false;
      // Qualifiers: observed, realtime
      // Dependencies: Valid only if entity is present
      // Persistent: N/A
      // Notification: no
      description "Entity product name";
    }

    leaf hw-version {
      type string;
      config false;
      // Qualifiers: observed, realtime
      // Dependencies: Valid only if entity is present
      // Persistent: N/A
      // Notification: no
      description "Entity hardware version";
    }

    leaf platform-name {
      type string;
      config false;
      // Qualifiers: observed, realtime
      // Dependencies: Valid only if entity is present
      // Persistent: N/A
      // Notification: no
      description "Entity platform name";
    }

    leaf ppid {
      type string;
      config false;
      // Qualifiers: observed, realtime
      // Dependencies: Valid only if entity is present
      // Persistent: N/A
      // Notification: no
      description "Entity PPID";
    }

    leaf part-number {
      type string;
      config false;
      // Qualifiers: observed, realtime
      // Dependencies: Valid only if entity is present
      // Persistent: N/A
      // Notification: no
      description "Entity Part Number";
    }

    leaf service-tag {
      type string;
      config false;
      // Qualifiers: observed, realtime
      // Dependencies: Valid only if entity is present
      // Persistent: N/A
      // Notification: no
      description "Entity service tag";
    }

    leaf service-code {
      type string;
      config false;
      // Qualifiers: observed, realtime
      // Dependencies: Valid only if entity is present
      // Persistent: N/A
      // Notification: no
      description "Entity service code";
    }
    description "Attributes of a chassis' or entity's EEPROM";
  }


  // Chassis grouping - Everything there is to know about a chassis
  //
  // Contains all attributes of a chassis, regardless of chassis type
  // (pizza box, controlling bridge or port extender) and stacking
  // (or not) configuration.

  grouping chassis {

    uses eeprom;  //ude EEPROM attributes

    leaf oper-status {
      type base-cmn:oper-status-type;
      config false;
      // Qualifiers: observed, realtime
      // Dependencies: None
      // Persistent: N/A
      // Notification: Yes; parameters (oper_status)
      // Notes: This attribute is normally "up".  Essentially, it reflects
      //        the result (status) of the last CPS get or set request for
      //        the object.  It will be set to "fail"
      //        if there was any failure in getting or setting any
      //        attribute for the last object get or set request.  Errors
      //        experienced when getting attributes are reflected in values
      //        returned for those attributes, e.g. an error in obtaining
      //        the power usage is reflected as returning -1 for the
      //        power-usage attribute.  If there were no errors for the
      //        last CPS request, this attribute will be set to "up".
      description "Operational status";
    }

    leaf fault-type {
      type fault-type;
      config false;
      // Qualifiers: observed, realtime
      // Dependencies: Valid only if oper-status == fail
      // Persistent: N/A
      // Notification: Yes; parameters (fault_type)
      description "Cause of fault";
    }

    leaf num_mac_addresses {
      type uint32;
      config false;
      // Qualifiers: observed, realtime
      // Dependencies: None
      // Persistent: N/A
      // Notification: no
      description "Number of MAC addresses assigned to chassis";
    }

    leaf base_mac_addresses {
      type base-cmn:mac-address;
      config false;
      // Qualifiers: observed, realtime
      // Dependencies: None
      // Persistent: N/A
      // Notification: no
      description "Base MAC addresses assigned to chassis";
    }

    leaf power-usage {
      type power-usage-type;
      config false;
      // Qualifiers: observed, realtime
      // Dependencies: May not be supported for all platforms.
      //               Value shall be 0 for unsupported platforms.
      // Persistent: N/A
      // Notification: No
      // Notes: A negative value indicates an error.
      description "Total power consumed by chassis";
    }

    leaf power-off {
      type boolean;
      config true;
      // Qualifiers: target
      // Dependencies: May not be supported for all platforms.
      //               On unsupported platforms, setting this attribute has
      //               no effect.
      // Persistent: N/A
      // Notification: No
      description "Kill power to chassis";
    }

    leaf active-rpm-slot {
      type uint8;
      config true;
      // Qualifiers: observed, realtime, target
      // Dependencies: May not be supported for all platforms.
      //               For those that do not support RPM redundancy, value is
      //               fixed to slot of single RPM, or single card for
      //               pizza-box or port extender chassis, and setting this
      //               attribute has no effect.
      // Default: N/A
      // Persistent: N/A
      // Notification: Yes; parameters (slot)
      // Notes: Writing a value different from the current observed/
      //        realtime value to the target qualifiers initiates an
      //        RPM switchover.
      description "Slot of active RPM";
    }

    leaf reboot {
      type reboot-type;
      config true;
      // Qualifiers: observed, realtime, target
      // Dependencies: Valid only if card is present
      // Persistent: N/A
      // Notification: no
      description "reboot type";
    }
    leaf reboot-reason {
      type string;
      default "Reboot reason not provided.";
      config true;
      // Qualifiers: observed, target
      // Persistent: yes
      // Notification: no
      description "Applications should use this attribute to provide a reboot reason.";
    }
    leaf dom {
      type boolean;
      config true;
      // Qualifiers: observed, realtime, target
      // Dependencies: None
      // Persistent: N/A
      // Notification: no
      description "Enable/Disable digital media monitoring (dom)";
    }
    description "Attributes of a chassis";
  }


  // Entity grouping - Everything there is to know about an entity (FRU)
  //
  // Contains all attributes of an entity within a chassis, which is a field-
  // replacable unit (FRU) part of a chassis (actual or virtual).  For
  // consistency, things that can be an FRU on any platform at treated as
  // FRUs, even if it is not an FRU for a given platform.  Thus, a card is
  // treated as an entity (FRU), even for a platform that does not have
  // cards -- a pizza-box chassis or port extender will have a single
  // (virtual) card entity, one that is always present.

  grouping entity {

    uses eeprom;        //ude EEPROM attributes

    leaf name {
      type string;
      config false;
      // Qualifiers: observed, realtime
      // Dependencies: None
      // Persistent: N/A
      // Notification: No
      description "Printable name of entity";
    }

    leaf present {
      type boolean;  // true <=> Entity present in slot
      config false;
      // Qualifiers: observed, realtime
      // Dependencies: None
      // Persistent: N/A
      // Notification: Yes; parameters (present)
      description "Entity present flag";
    }

    leaf insertion-cnt {
      type yang:gauge64;
      config true;
      // Qualifiers: observed, realtime, target
      // Dependencies: None
      // Persistent: Across process restart: yes
      //             Across kernel restart:  yes
      //             Across power cycle:     yes
      // Notification: No
      // Notes: Writing any value for this attribute to the target space
      //        has the effect of resetting this counter to 0.
      description "Number of times entity inserted";
    }

    leaf insertion-timestamp {
      type yang:timestamp;
      config false;
      // Qualifiers: observed, realtime
      // Dependencies: None
      // Persistent: Across process restart: yes
      //             Across kernel restart:  yes
      //             Across power cycle:     yes
      // Notification: No
      description "Timestamp of last entity insertion";
    }

    leaf admin-status {
      type base-cmn:admin-status-type;
      config true;
      // Qualifiers: observed, realtime, target
      // Dependencies: None
      // Default: up
      // Persistent: Across process restart: Yes
      //             Across kernel restart:  No
      //             Across power cycle:     No
      // Notification: Yes; parameters (admin_status)
      // Notes: Up <=> Polling of entity enabled, CPS/FUSE requests
      //               satisfied
      //        Down <=> Polling of entity disabled, CPS/FUSE requests
      //                 rejected
      //        Testing <=> As with down, but also includes others in
      //                    same diag class
      description "Administrative status";
    }

    leaf oper-status {
      type base-cmn:oper-status-type;
      config false;
      // Qualifiers: observed, realtime
      // Dependencies: !present => oper-status == unknown
      //               admin-status == testing => oper-status == down
      // Persistent: N/A
      // Notification: Yes; parameters (oper_status)
      description "Operational status";
    }

    leaf fault-type {
      type fault-type;
      config false;
      // Qualifiers: observed, realtime
      // Dependencies: Valid only if oper-status == fail
      // Persistent: N/A
      // Notification: Yes; parameters (fault_type)
      description "Cause of fault";
    }

    // The following attributes apply only to entities of type card

    choice entity-type-choice {
      case card {
        leaf power-on {
          type boolean;  // true <=> Power to entity enabled
          config true;
          // Qualifiers: observed, realtime, target
          // Dependencies: Only applicable to card entities
          // Default: false
          // Persistent: Across process restart: yes
          //             Across kernel restart:  yes
          //             Across power cycle:     no
          // Notification: No
          description "Power control for entity";
        }

        leaf reboot {
          type reboot-type;
          config true;
          // Qualifiers: observed, realtime, target
          // Dependencies: Valid only if card is present
          // Persistent: N/A
          // Notification: no
          description "reboot type";
        }
      }
      description "Type of an entity";
    }
    description "Attributes of an entity (FRU)";
  }


  // PSU grouping - Everything there is to know about a PSU
  //
  // This grouping serves as an extension of the entity grouping
  // for PSUs.

  grouping psu {

    leaf input-type {
      type input-power-type;
      config false;
      // Qualifiers: observed, realtime
      // Dependencies: Valid only if entity is present
      // Persistent: N/A
      // Notification: no
      description "Input current type";
    }

    leaf fan-airflow-type {
      type fan-airflow-type;
      config false;
      // Qualifiers: observed, realtime
      // Dependencies: Valid only if entity is present
      // Persistent: N/A
      // Notification: no
      description "Direction of airflow for PSU fan(s)";
    }
    description "Attributes of a power supply";
  }


  // Fan tray grouping - Everything there is to know about a fan tray
  //
  // This grouping serves as an extension to the entity grouping for
  // fan trays.

  grouping fan-tray {

    leaf fan-airflow-type {
      type fan-airflow-type;
      config false;
      // Qualifiers: observed, realtime
      // Dependencies: Valid only if entity is present
      // Persistent: N/A
      // Notification: no
      description "Direction of airflow for fans";
    }
    description "Attributes of a fan tray";
  }


  // Card grouping - Everything there is to know about a card
  //
  // This grouping serves as an extenstion of the entity grouping for
  // cards.  Note that for platforms that do not have actual field-replacable
  // cards, such as a pizza-box or port-extender chassis, there still be card
  // entities -- exactly 1 (virtual) card, in 1 (virtual) slot, which can
  // never be removed (i.e. will always show as present).

  grouping card {

    leaf card-type {
      type card-type-type;
      config false;
      // Qualifiers: observed, realtime
      // Dependencies: Valid only if entity is present
      // Persistent: N/A
      // Notification: no
      description "Type of card";
    }
    description "Attributes of a card";
  }


  // Fan grouping - Everything there is to know about a fan

  grouping fan {

    leaf oper-status {
      type base-cmn:oper-status-type;
      config false;
      // Qualifiers: observed, realtime
      // Dependencies: Valid only if entity present.
      //               admin-status(entity) == testing => oper-status == down.
      // Persistent: N/A
      // Notification: Yes; parameters (oper_status)
      description "Operational status";
    }

    leaf fault-type {
      type fault-type;
      config false;
      // Qualifiers: observed, realtime
      // Dependencies: Valid only if entity present and
      //               if oper-status == fail
      // Persistent: N/A
      // Notification: Yes; parameters (fault_type)
      description "Cause of fault";
    }

    leaf speed {
      type fan-speed-type;
      config true;
      // Qualifiers: observed, realtime, target
      // Dependencies: Valid only if entity present
      // Default: Maximum speed for fan (see below)
      // Persistent: N/A
      // Notification: No
      // Notes: A fault is indicated (see above) if a fan's current speed
      //        is not what the target speed specified
      description "Fan speed, in RPM";
    }

    leaf speed_pct {
      type uint8;
      config true;
      // Qualifiers: observed, realtime, target
      // Dependencies: Valid only if entity present
      // Default: Maximum speed for fan (see below)
      // Persistent: N/A
      // Notification: No
      // Notes: A fault is indicated (see above) if a fan's current speed
      //        is not what the target speed specified
      description "Fan speed, as % of maximum";
    }

    leaf max_speed {
      type fan-speed-type;
      config false;
      // Qualifiers: observed, realtime
      // Dependencies: Valid only if entity present
      // Persistent: N/A
      // Notification: No
      description "Maximum speed of fan, in RPM";
    }
    description "Attributes of a (PSU or fan tray) fan";
  }


  // LED grouping - Everything there is to know about an LED

  grouping led {

    leaf oper-status {
      type base-cmn:oper-status-type;
      config false;
      // Qualifiers: observed, realtime
      // Dependencies: Valid only if entity present.
      //               admin-status == testing => oper-status == down.
      // Persistent: N/A
      // Notification: Yes; parameters (oper_status)
      description "Operational status";
    }

    leaf fault-type {
      type fault-type;
      config false;
      // Qualifiers: observed, realtime
      // Dependencies: Valid only if entity present and
      //               if oper-status == fail
      // Persistent: N/A
      // Notification: Yes; parameters (fault_type)
      description "Cause of fault";
    }

    leaf req_on {
      type boolean;  // true <=> LED on
      config true;
      // Qualifiers: observed, realtime, target
      // Dependencies: Valid only if entity present.
      //               Either 'on' or 'message' attribute supported,
      //               depending on platform.
      // Default: false
      // Persistent: Across process restarts: Yes
      //             Across kernel restarts:  No
      //             Across power cycles:     No
      // Notification: No
      description "Illumination state of LED requested by application";
    }

    leaf on {
      type boolean;  // true <=> LED on
      config true;
      // Qualifiers: observed, realtime, target
      // Dependencies: Valid only if entity present.
      //               Either 'on' or 'message' attribute supported,
      //               depending on platform.
      // Default: false
      // Persistent: Across process restarts: Yes
      //             Across kernel restarts:  No
      //             Across power cycles:     No
      // Notification: No
      description "Illumination state of physical LED";
    }
    description "Attributes of an LED";
  }


  // Display grouping - Everything there is to know about a text message
  //                    display

  grouping display {

    leaf oper-status {
      type base-cmn:oper-status-type;
      config false;
      // Qualifiers: observed, realtime
      // Dependencies: Valid only if entity present.
      //               admin-status == testing => oper-status == down.
      // Persistent: N/A
      // Notification: Yes; parameters (oper_status)
      description "Operational status";
    }

    leaf on {
      type boolean;  // true <=> Digit Display LED on
      config true;
      // Qualifiers: observed, realtime, target
      // Dependencies: Valid only if entity present.
      //               Either 'on' or 'message' attribute supported,
      //               depending on platform.
      // Default: false
      // Persistent: Across process restarts: Yes
      //             Across kernel restarts:  No
      //             Across power cycles:     No
      // Notification: No
      description "Power state of physical Digit Display LED";
    }

    leaf fault-type {
      type fault-type;
      config false;
      // Qualifiers: observed, realtime
      // Dependencies: Valid only if entity present and
      //               if oper-status == fail
      // Persistent: N/A
      // Notification: Yes; parameters (fault_type)
      description "Cause of fault";
    }

    leaf message {
      type string;
      config true;
      // Qualifiers: observed, realtime, target
      // Dependencies: Valid only if entity present.
      //               Either 'on' or 'message' attribute supported,
      //               depending on platform.
      // Default: ""
      // Persistent: Across process restarts: Yes
      //             Across kernel restarts:  No
      //             Across power cycles:     No
      // Notification: No
      description "Message to display in text display";
    }
    description "Attributes of a text message display";
  }


  // Temperature sensor grouping - Everything there is to know about a
  //                               temperature sensor

  grouping temperature {

    leaf oper-status {
      type base-cmn:oper-status-type;
      config false;
      // Qualifiers: observed, realtime
      // Dependencies: Valid only if entity present.
      //               admin-status == testing => oper-status == down.
      // Persistent: N/A
      // Notification: Yes; parameters (oper_status)
      description "Operational status";
    }

    leaf fault-type {
      type fault-type;
      config false;
      // Qualifiers: observed, realtime
      // Dependencies: Valid only if entity present and
      //               if oper-status == fail
      // Persistent: N/A
      // Notification: Yes; parameters (fault_type)
      description "Cause of fault";
    }

    leaf temperature {
      type temperature-type;
      config false;
      // Qualifiers: observed, realtime
      // Dependencies: Valid only if entity present
      // Persistent: N/A
      // Notification: No
      description "Current temperature";
    }

    leaf shutdown_threshold {
      type temperature-type;
      config true;
      // Qualifiers: observed, realtime, target
      // Dependencies: Valid only if entity present
      // Default: Not set
      // Persistent: No
      // Notification: No
      description "Threshold for hardware-based shutdown";
    }

    leaf thresh-enable {
      type boolean;
      config true;
      // Qualifiers: observed, realtime, target
      // Dependencies: Valid only if entity present
      // Default: False
      // Persistent: No
      // Notification: No
      description "Enable threshold detection";
    }

    leaf last-thresh {
      type temperature-type;
      config false;
      // Qualifiers: observed, realtime, target
      // Dependencies: Valid only if entity present and threshold crossed
      // Default: Not set
      // Persistent: No
      // Notification: Yes
      description "Last threshold temperature crossed";
    }
    description "Attributes of a temperature sensor";
  }


  // Temperature sensor range threshold grouping - Everything there is
  //                                               to know about
  //                                               temperature ranges

  grouping temp_threshold {

    leaf hi {
      type temperature-type;
      config true;
      // Qualifiers: observed, realtime, target
      // Dependencies: Valid only if entity present
      // Default: Not set
      // Persistent: No
      // Notification: No
      description "Threshold for increasing temperature";
    }

    leaf lo {
      type temperature-type;
      config true;
      // Qualifiers: observed, realtime, target
      // Dependencies: Valid only if entity present
      // Default: Not set
      // Persistent: No
      // Notification: No
      description "Threshold for decreasing temperature";
    }
    description "Attributes of a temperature sensor threshold";
  }

  /* Power Monitor grouping
   * - Everything there is to know about an Input Power monitor
   * Which is the total power consumed by the system (including PSU loss)
   */

  grouping power-monitor {

    leaf voltage {
      type common:xfloat;
      units "Volts";
      config false;
      // Qualifiers: observed, realtime
      // Dependencies: Valid only if entity present.
      // Persistent: No
      // Notification: No
      description "Input Voltage value";
    }

    leaf current {
      type common:xfloat;
      units "Amps";
      config false;
      // Qualifiers: observed, realtime
      // Dependencies: Valid only if entity present.
      // Persistent: No
      // Notification: No
      description "Input Current value";
    }

    leaf power {
      type common:xfloat;
      units "Watts";
      config false;
      // Qualifiers: observed, realtime
      // Dependencies: Valid only if entity present.
      // Persistent: No
      // Notification: No
      description "Input Power value";
    }
    description "Attributes of an input power monitor";
  }

  // PLD grouping - Everything there is to know about programmable logic
  //                devices (PLDs)

  grouping pld {

    leaf version {
      type string;
      config false;
      // Qualifiers: observed, realtime
      // Dependencies: Valid only if entity present
      // Persistent: N/A
      // Notification: No
      description "PLD firmware version";
    }
    description "Attributes of a programmable logic device (PLD)";
  }


  // Port module grouping - Everything there is no know about linecard
  //                        port modules

  grouping port-module {

    leaf present {
      type boolean;  // true <=> Module present in module slot
      config false;
      // Qualifiers: observed, realtime
      // Dependencies: None
      // Persistent: N/A
      // Notification: Yes; parameters (present)
      description "Module present flag";
    }

    leaf insertion-cnt {
      type yang:gauge64;
      config true;
      // Qualifiers: observed, realtime, target
      // Dependencies: None
      // Persistent: Across process restart: yes
      //             Across kernel restart:  yes
      //             Across power cycle:     yes
      // Notification: No
      // Notes: Writing any value for this attribute to the target space
      //        has the effect of resetting this counter to 0.
      description "Number of times module inserted";
    }

    leaf insertion-timestamp {
      type yang:timestamp;
      config false;
      // Qualifiers: observed, realtime
      // Dependencies: None
      // Persistent: Across process restart: yes
      //             Across kernel restart:  yes
      //             Across power cycle:     yes
      // Notification: No
      description "Timestamp of last module insertion";
    }

    leaf admin-status {
      type base-cmn:admin-status-type;
      config true;
      // Qualifiers: observed, realtime, target
      // Dependencies: None
      // Default: up
      // Persistent: Across process restart: Yes
      //             Across kernel restart:  No
      //             Across power cycle:     No
      // Notification: Yes; parameters (admin_status)
      // Notes: Up <=> Polling of module enabled, CPS/FUSE requests
      //               satisfied
      //        Down <=> Polling of module disabled, CPS/FUSE requests
      //                 rejected
      //        Testing <=> As with down, but also includes others in
      //                    same diag class
      description "Administrative status";
    }

    leaf oper-status {
      type base-cmn:oper-status-type;
      config false;
      // Qualifiers: observed, realtime
      // Dependencies: !present => oper-status == unknown.
      //               admin-status == testing => oper-status == down.
      // Persistent: N/A
      // Notification: Yes; parameters (oper_status)
      description "Operational status";
    }

    leaf fault-type {
      type fault-type;
      config false;
      // Qualifiers: observed, realtime
      // Dependencies: Valid only if oper-status == fail
      // Persistent: N/A
      // Notification: Yes; parameters (fault_type)
      description "Cause of fault";
    }
    description "Attributes of a linecard port module";

    // TBD
  }

  /* PAS Media releated configuration grouping */

  grouping pas-media-config {

    leaf lock-down-status {

      type boolean;
      config true;
      description "Lock down feature status.";
    }

    leaf led-control {

      type boolean;
      config false;
      description "LED control flag";
    }

    leaf identification-led-control {
      type boolean;
      config false;
      description "Identification LED control flag, PAS owns front panel port identification
                   led control if this attribute value is True";
    }
    description "Attributes of PAS media configuration.";
  }


  // Optical media adapter grouping - Everything there is to know about
  //                                  optical media adapters

  grouping media {

    leaf present {
      type boolean;  // true <=> Module present in port slot
      config false;
      // Qualifiers: observed, realtime
      // Dependencies: None
      // Persistent: N/A
      // Notification: Yes; parameters (present)
      description "Adapter present flag";
    }

    leaf port-type {
      type port-type;
      config false;
      // Qualifiers: observed, realtime
      // Dependencies: None
      // Persistent: N/A
      // Notification: No
      description "Media type is pluggable or fixed or backplane or ...";
    }

    leaf max-port-power-milliwatts {
      type uint32;
      config false;
      // Qualifiers: observed, realtime
      // Dependencies: None
      // Persistent: N/A
      // Notification: No
      description "This is the maximum power (in milliwats) that the port can provide";
    }

    leaf max-media-power-milliwatts {
      type uint32;
      config false;
      // Qualifiers: observed, realtime
      // Dependencies: None
      // Persistent: N/A
      // Notification: No
      description "This is the maximum power (in milliwats) that the inserted media can draw";
    }

    leaf power-limit-flag {
      type boolean;
      config false;
      // Qualifiers: observed, realtime
      // Dependencies: None
      // Persistent: N/A
      // Notification: No
      description "This flag states if the connected device can draw more power than the port can provide. Flag is set if max-port-power-milliwatts < max-media-power-milliwatts";
    }

    leaf qsa-adapter {
      type qsa-adapter;
      config false;
      // Qualifiers: observed, realtime
      // Dependencies: None
      // Persistent: N/A
      // Notification: No
      description "QSA adapter tpe connected, if any";
    }

    leaf qsa28-expected {
      type boolean;
      config false;
      // Qualifiers: observed, realtime
      // Dependencies: None
      // Persistent: N/A
      // Notification: No
      description "QSA adapter type connected is QSA when QSA28 is expected";
    }

    leaf connector-separable {
      type boolean;
      config false;
      // Qualifiers: observed, realtime
      // Dependencies: None
      // Persistent: N/A
      // Notification: No
      description "Is the media connector separable";
    }

    leaf cable-length-cm {
      type uint32;
      config false;
      // Qualifiers: observed, realtime
      // Dependencies: None
      // Persistent: N/A
      // Notification: No
      description "Cable length in cm";
    }

    leaf ext-spec-compliance-code {
      type ext_spec_compliance_code;
      config false;
      // Qualifiers: observed, realtime
      // Dependencies: None
      // Persistent: N/A
      // Notification: No
      description "Extended specification compliance code. Used for 25G NRZ based DAC.";
    }

    leaf media-interface-lane-count {
      type uint32;
      config false;
      // Qualifiers: observed, realtime
      // Dependencies: None
      // Persistent: N/A
      // Notification: No
      description "Number of transmission lanes";
    }

    leaf media-interface {
      type media-interface;
      config false;
      // Qualifiers: observed, realtime
      // Dependencies: None
      // Persistent: N/A
      // Notification: No
      description "Media interface specifier";
    }

    leaf media-interface-qualifier {
      type media-interface-qualifier;
      config false;
      // Qualifiers: observed, realtime
      // Dependencies: None
      // Persistent: N/A
      // Notification: No
      description "Media interface qualifier specifier";
    }

    leaf cable-type {
      type media-cable-type;
      config false;
      // Qualifiers: observed, realtime
      // Dependencies: None
      // Persistent: N/A
      // Notification: No
      description "Media cable type";
    }

    leaf connector-type {
      type media-connector-type;
      config false;
      // Qualifiers: observed, realtime
      // Dependencies: None
      // Persistent: N/A
      // Notification: No
      description "Media connector type";
    }

    leaf initial-polling-delay-ms {
      type uint32;
      config false;
      // Qualifiers: observed, realtime
      // Dependencies: None
      // Persistent: N/A
      // Notification: No
      description "Time delay (in ms) before media EEPROM is polled";
    }

    leaf device-ready {
      type boolean;
      config false;
      // Qualifiers: observed, realtime
      // Dependencies: None
      // Persistent: N/A
      // Notification: No
      description "Specifies if the media is ready for probing and use";
    }

    leaf display-string {
      type string;
      config false;
      description "String to be used to display media name";
    }

    leaf media-name {
      type string;
      config false;
      description "This name is used to refer to the media type. It can differ from display string since display string has additional info";
    }

    leaf category-string {
      type string;
      config false;
      description "This string is used to refer to the media category (SFP, SFP+, QSFP+ etc). This string is used for display purposes";
    }

    leaf lockdown-state {
      type boolean;
      config false;
      // Qualifiers: observed, realtime
      // Dependencies: None
      // Persistent: N/A
      // Notification: No
      description "This is whether or not the media is locked";
    }

    leaf channel-count {
      type uint32;
      config false;
      // Qualifiers: observed, realtime
      // Dependencies: None
      // Persistent: N/A
      // Notification: No
      description "This is the number of channels in the device";
    }

    leaf default-media-speed {
      type base-if:speed;
      config false;
      description "The default speed of the device inserted";
    }

    leaf default-breakout-mode {
      type base-cmn:breakout-type;
      config false;
      description "This is the physical (hence default) breakout property of the media type";
    }

    leaf default-breakout-speed {
      type base-if:speed;
      config false;
      description "The default speed of the individual breakouts";
    }

    leaf default-phy-mode {
      type base-if:phy-mode-type;
      config false;
      description "The default PHY mode";
    }

    leaf default-autoneg {
      type base-if:supported-autoneg;
      config false;
      description "The default autonegotiation value";
    }

    leaf default-fec {
      type base-cmn:fec-type;
      config false;
      description "The default FEC value";
    }

    leaf-list sub-port-id {
      type uint32;
      config false;
      // Dependencies: Number of items in list is the port density for that port
      description "The effective id for that port. Normally a single number except in cases where a port has >1 density; for example QSFP28-DD. List length is port density";
    }

    leaf port-density {
      type uint32;
      config false;
      // Notes: Default is 1 since most ports map to 1 logical port
      description "Used to account for ports that have multiple logical ports; example QSFP28-DD. This is also the number of sub-port-ids";
    }

    leaf insertion-cnt {
      type yang:gauge64;
      config true;
      // Qualifiers: observed, realtime, target
      // Dependencies: None
      // Persistent: Across process restart: yes
      //             Across kernel restart:  yes
      //             Across power cycle:     yes
      // Notification: No
      // Notes: Writing any value for this attribute to the target space
      //        has the effect of resetting this counter to 0.
      description "Number of times adapter inserted";
    }

    leaf insertion-timestamp {
      type yang:timestamp;
      config false;
      // Qualifiers: observed, realtime
      // Dependencies: None
      // Persistent: Across process restart: yes
      //             Across kernel restart:  yes
      //             Across power cycle:     yes
      // Notification: No
      description "Timestamp of last adapter insertion";
    }

    leaf admin-status {
      type base-cmn:admin-status-type;
      config true;
      // Qualifiers: observed, realtime, target
      // Dependencies: None
      // Default: up
      // Persistent: Across process restart: Yes
      //             Across kernel restart:  No
      //             Across power cycle:     No
      // Notification: Yes; parameters (admin_status)
      // Notes: Up <=> Polling of module enabled, CPS/FUSE requests
      //               satisfied
      //        Down <=> Polling of module disabled, CPS/FUSE requests
      //                 rejected
      //        Testing <=> As with down, but also includes others in
      //                    same diag class
      description "Administrative status";
    }

    leaf oper-status {
      type base-cmn:oper-status-type;
      config false;
      // Qualifiers: observed, realtime
      // Dependencies: !present => oper-status == unknown.
      //               admin-status == testing => oper-status == down.
      // Persistent: N/A
      // Notification: Yes; parameters (oper_status)
      description "Operational status";
    }
    leaf support-status {
      type media-support-status;
      config false;
      description "Media support status.";
    }

    leaf category {
      type media-category;
      config false;
      // Qualifiers: observed, realtime
      // Dependencies: Valid only if present = true
      // Persistent: N/A
      // Notification: No
      description "Media category";
    }

    leaf type {
      type media-type;
      config false;
      // Qualifiers: observed, realtime
      // Dependencies: Valid only if present = true
      // Persistent: N/A
      // Notification: No
      description "Media type";
    }

    leaf capability {
      type base-if:speed;
      config false;
      // Qualifiers: observed, realtime
      // Dependencies: Valid only if present = true
      // Persistent: N/A
      // Notification: No
      description "Media speed capability";
    }

    leaf vendor-id {
      type binary {
        length "3";
      }
      config false;
      // Qualifiers: observed, realtime
      // Dependencies: Valid only if present = true
      // Persistent: N/A
      // Notification: No
      description "Vendor id of the physical media";
    }

    leaf serial-number {
      type string {
        length "17";
      }
      config false;
      // Qualifiers: observed, realtime
      // Dependencies: Valid only if present = true
      // Persistent: N/A
      // Notification: No
      description "Serial number of the physical media";
    }

    leaf qualified {
      type boolean; // true <=> If it is vendor qualified media
      config false;
      // Qualifiers: observed, realtime
      // Dependencies: Valid only if present = true
      // Persistent: N/A
      // Notification: No
      description "Is qualified or not";
    }

    leaf high-power-mode {
      type boolean; // true <=> If its enable
      config true;
      // Qualifiers: observed, realtime
      // Dependencies: Valid only if present = true
      // Persistent: N/A
      // Notification: No
      description "Enable high power mode";
    }

    leaf identifier {
      type uint32;
      config false;
      // Qualifiers: observed, realtime
      // Dependencies: Valid only if present = true
      // Persistent: N/A
      // Notification: No
      description "Type of serial transceiver";
    }

    leaf ext-identifier {
      type uint32;
      config false;
      // Qualifiers: observed, realtime
      // Dependencies: Valid only if present = true
      // Persistent: N/A
      // Notification: No
      description "Extended identifier of type of serial transceiver";
    }

    leaf connector {
      type uint32;
      config false;
      // Qualifiers: observed, realtime
      // Dependencies: Valid only if present = true
      // Persistent: N/A
      // Notification: No
      description "Code for connector type";
    }

    leaf transceiver {
      type binary {
        length "8";
      }
      config false;
      // Qualifiers: observed, realtime
      // Dependencies: Valid only if present = true
      // Persistent: N/A
      // Notification: No
      description "Code for electronic or optical compatibility";
    }
    leaf encoding {
      type uint32;
      config false;
      // Qualifiers: observed, realtime
      // Dependencies: Valid only if present = true
      // Persistent: N/A
      // Notification: No
      description "Code for serial encoding algorithm";
    }
    leaf br-nominal  {
      type uint32;
      config false;
      // Qualifiers: observed, realtime
      // Dependencies: Valid only if present = true
      // Units: 100 MBps
      // Persistent: N/A
      // Notification: No
      description "Nominal signaling rate, units of 100Mbits/sec ";
    }
    leaf rate-identifier  {
      type uint32;
      config false;
      // Qualifiers: observed, realtime
      // Dependencies: Valid only if present = true
      // Persistent: N/A
      // Notification: No
      description "Type of rate select functionality";
    }

    leaf length-sfm-km {
      type uint32;
      config false;
      // Qualifiers: observed, realtime
      // Dependencies: Valid only if present = true
      // Units: km
      // Persistent: N/A
      // Notification: No
      description "Link length supported for SMF fiber in km";
    }

    leaf length-sfm {
      type uint32;
      config false;
      // Qualifiers: observed, realtime
      // Dependencies: Valid only if present = true
      // Units: 100m
      // Persistent: N/A
      // Notification: No
      description "Link length supported for single mode fiber, units of 100m";
    }

    leaf length-om2 {
      type uint32;
      config false;
      // Qualifiers: observed, realtime
      // Dependencies: Valid only if present = true
      // Units: 10m
      // Persistent: N/A
      // Notification: No
      description "Link length supported for 50um OM2 fiber, units of 10m";
    }

    leaf length-om1 {
      type uint32;
      config false;
      // Qualifiers: observed, realtime
      // Dependencies: Valid only if present = true
      // Units: 10m
      // Persistent: N/A
      // Notification: No
      description "Link length supported for 62.5um OM1 fiber, units of 10m";
    }

    leaf length-cable {
      type uint32;
      config false;
      // Qualifiers: observed, realtime
      // Dependencies: Valid only if present = true
      // Units: m
      // Persistent: N/A
      // Notification: No
      description "Link length supported for copper or direct attach cable, units of m";
    }

    leaf length-om3 {
      type uint32;
      config false;
      // Qualifiers: observed, realtime
      // Dependencies: Valid only if present = true
      // Units: 10m
      // Persistent: N/A
      // Notification: No
      description "Link length supported for 50um OM3 fiber, units of 10m";
    }

    leaf vendor-name  {
      type string {
        length "17";
      }
      config false;
      // Qualifiers: observed, realtime
      // Dependencies: Valid only if present = true
      // Persistent: N/A
      // Notification: No
      description "Vendor name (ASCII)";
    }

    leaf ext-transceiver  {
      type uint32;
      config false;
      // Qualifiers: observed, realtime
      // Dependencies: Valid only if present = true
      // Persistent: N/A
      // Notification: No
      description "Extended Transceiver Codes";
    }

    leaf vendor-pn {
      type string {
        length "17";
      }
      config false;
      // Qualifiers: observed, realtime
      // Dependencies: Valid only if present = true
      // Persistent: N/A
      // Notification: No
      description "Part number provided by SFP+ transceiver vendor (ASCII)";
    }

    leaf vendor-rev {
      type binary {
        length "2";
      }
      config false;
      // Qualifiers: observed, realtime
      // Dependencies: Valid only if present = true
      // Persistent: N/A
      // Notification: No
      description "Revision level for part number provided by vendor (ASCII)";
    }

    leaf wavelength {
      type uint32;
      units "nm";
      config false;
      // Qualifiers: observed, realtime
      // Dependencies: Valid only if present = true
      // Persistent: N/A
      // Notification: No
      description "Laser wavelength (Passive/Active Cable Specification Compliance)";
    }

    leaf wavelength-pico-meters {
      type uint32;
      units "pm";
      config false;
      // Qualifiers: observed, realtime
      // Dependencies: Valid only if present = true
      // Persistent: N/A
      // Notification: No
      description "Laser wavelength (Passive/Active Cable Specification Compliance), in picometer units. Should be more precise than the wavelength field in nanometers";
    }

    choice media-category {
      case qsfp-plus {
        leaf wavelength-tolerance {
          type uint32;
          config false;
          // Qualifiers: observed, realtime
          // Dependencies: Valid only if present = true
          // Persistent: N/A
          // Notification: No
          description "Guaranteed range of laser wavelength";
        }
        leaf max-case-temp {
          type uint32;
          config false;
          // Qualifiers: observed, realtime
          // Dependencies: Valid only if present = true
          // Persistent: N/A
          // Notification: No
          description "Maximum Case Temperature in Degrees C";
        }
      }
      case sfp-plus {
        leaf br-max{
          type uint32;
          config false;
          // Qualifiers: observed, realtime
          // Dependencies: Valid only if present = true
          // Units: Percent
          // Persistent: N/A
          // Notification: No
          description "Upper bit rate margin, units of % ";
        }

        leaf br-min {
          type uint32;
          config false;
          // Qualifiers: observed, realtime
          // Dependencies: Valid only if present = true
          // Units: Percent
          // Persistent: N/A
          // Notification: No
          description "Lower bit rate margin, units of %";
        }

        leaf sff-8472-compliance {
          type uint32;
          config false;
          // Qualifiers: observed, realtime
          // Dependencies: Valid only if present = true
          // Persistent: N/A
          // Notification: No
          description "Indicates which revision of SFF-8472 the transceiver complies with";
        }
      }
      description "Media Types.";
    }

    leaf cc_base {
      type uint32;
      config false;
      // Qualifiers: observed, realtime
      // Dependencies: Valid only if present = true
      // Persistent: N/A
      // Notification: No
      description "Check code for Base ID Fields (addresses 0 to 62)";
    }

    leaf options {
      type uint32;
      config false;
      // Qualifiers: observed, realtime
      // Dependencies: Valid only if present = true
      // Persistent: N/A
      // Notification: No
      description "Indicates which optional SFP+ signals are implemented";
    }

    leaf date-code {
      type binary {
        length "8";
      }
      config false;
      // Qualifiers: observed, realtime
      // Dependencies: Valid only if present = true
      // Persistent: N/A
      // Notification: No
      description "Vendor's manufacturing date code";
    }

    leaf diag-mon-type{
      type uint32;
      config false;
      // Qualifiers: observed, realtime
      // Dependencies: Valid only if present = true
      // Persistent: N/A
      // Notification: No
      description "Indicates which type of diagnostic monitoring is implemented (if any)";
    }

    leaf enhanced-options {
      type uint32;
      config false;
      // Qualifiers: observed, realtime
      // Dependencies: Valid only if present = true
      // Persistent: N/A
      // Notification: No
      description "Indicates which optional enhanced features are implemented (if any)";
    }

    leaf cc_ext {
      type uint32;
      config false;
      // Qualifiers: observed, realtime
      // Dependencies: Valid only if present = true
      // Persistent: N/A
      // Notification: No
      description "Check code for the Extended ID Fields (addr. 64 to 94)";
    }

    leaf vendor-Specific {
      type binary;
      config false;
      // Qualifiers: observed, realtime
      // Dependencies: Valid only if present = true
      // Persistent: N/A
      // Notification: No
      description "Vendor Specific EEPROM";
    }

    leaf rate-select-state {
      type boolean;
      config false;
      // Qualifiers: observed, realtime
      // Dependencies: None
      // Persistent: N/A
      // Notification: Yes; parameters (present)
      description "Rate select state";
    }

    leaf rx-power-measurement-type {
      type power-measurement-type;
      config false;
      // Qualifiers: observed, realtime
      // Dependencies: Valid only if present = true
      // Persistent: N/A
      // Notification: No
      description "Received power measurement type";
    }


    // Media Alarm and Warning thresholds

    leaf temp-high-alarm-threshold {
      type common:xfloat;
      config false;
      // Qualifiers: observed, realtime
      // Dependencies: Valid only if present = true
      // Persistent: N/A
      // Notification: No
      description "Temperature High alarm";
    }

    leaf temp-low-alarm-threshold {
      type common:xfloat;
      config false;
      // Qualifiers: observed, realtime
      // Dependencies: Valid only if present = true
      // Persistent: N/A
      // Notification: No
      description "Temperature Low alarm";
    }

    leaf temp-high-warning-threshold {
      type common:xfloat;
      config false;
      // Qualifiers: observed, realtime
      // Dependencies: Valid only if present = true
      // Persistent: N/A
      // Notification: No
      description "Temperature High warning";
    }

    leaf temp-low-warning-threshold {
      type common:xfloat;
      config false;
      // Qualifiers: observed, realtime
      // Dependencies: Valid only if present = true
      // Persistent: N/A
      // Notification: No
      description "Temperature Low warning";
    }

    leaf voltage-high-alarm-threshold {
      type common:xfloat;
      units "mV";
      config false;
      // Qualifiers: observed, realtime
      // Dependencies: Valid only if present = true
      // Persistent: N/A
      // Notification: No
      description "Voltage High alarm";
    }

    leaf voltage-low-alarm-threshold {
      type common:xfloat;
      units "mV";
      config false;
      // Qualifiers: observed, realtime
      // Dependencies: Valid only if present = true
      // Persistent: N/A
      // Notification: No
      description "Voltage Low alarm";
    }

    leaf voltage-high-warning-threshold {
      type common:xfloat;
      units "mV";
      config false;
      // Qualifiers: observed, realtime
      // Dependencies: Valid only if present = true
      // Persistent: N/A
      // Notification: No
      description "Voltage High warning";
    }

    leaf voltage-low-warning-threshold {
      type common:xfloat;
      units "mV";
      config false;
      // Qualifiers: observed, realtime
      // Dependencies: Valid only if present = true
      // Persistent: N/A
      // Notification: No
      description "Voltage Low warning";
    }

    leaf rx-power-high-alarm-threshold {
      type common:xfloat;
      units "mW";
      config false;
      // Qualifiers: observed, realtime
      // Dependencies: Valid only if present = true
      // Persistent: N/A
      // Notification: No
      description "RX Power High alarm";
    }

    leaf rx-power-low-alarm-threshold {
      type common:xfloat;
      units "mW";
      config false;
      // Qualifiers: observed, realtime
      // Dependencies: Valid only if present = true
      // Persistent: N/A
      // Notification: No
      description "RX Power Low alarm";
    }

    leaf rx-power-high-warning-threshold {
      type common:xfloat;
      units "mW";
      config false;
      // Qualifiers: observed, realtime
      // Dependencies: Valid only if present = true
      // Persistent: N/A
      // Notification: No
      description "RX Power High warning";
    }

    leaf rx-power-low-warning-threshold {
      type common:xfloat;
      units "mW";
      config false;
      // Qualifiers: observed, realtime
      // Dependencies: Valid only if present = true
      // Persistent: N/A
      // Notification: No
      description "RX Power Low warning";
    }

    leaf bias-high-alarm-threshold {
      type common:xfloat;
      units "mA";
      config false;
      // Qualifiers: observed, realtime
      // Dependencies: Valid only if present = true
      // Persistent: N/A
      // Notification: No
      description "Bias High alarm";
    }

    leaf bias-low-alarm-threshold {
      type common:xfloat;
      units "mA";
      config false;
      // Qualifiers: observed, realtime
      // Dependencies: Valid only if present = true
      // Persistent: N/A
      // Notification: No
      description "Bias Low alarm";
    }

    leaf bias-high-warning-threshold {
      type common:xfloat;
      units "mA";
      config false;
      // Qualifiers: observed, realtime
      // Dependencies: Valid only if present = true
      // Persistent: N/A
      // Notification: No
      description "Bias High warning";
    }

    leaf bias-low-warning-threshold {
      type common:xfloat;
      units "mA";
      config false;
      // Qualifiers: observed, realtime
      // Dependencies: Valid only if present = true
      // Persistent: N/A
      // Notification: No
      description "Bias Low warning";
    }

    leaf tx-power-high-alarm-threshold {
      type common:xfloat;
      units "mW";
      config false;
      // Qualifiers: observed, realtime
      // Dependencies: Valid only if present = true
      // Persistent: N/A
      // Notification: No
      description "Tx power High alarm";
    }

    leaf tx-power-low-alarm-threshold {
      type common:xfloat;
      units "mW";
      config false;
      // Qualifiers: observed, realtime
      // Dependencies: Valid only if present = true
      // Persistent: N/A
      // Notification: No
      description "Tx power Low alarm";
    }

    leaf tx-power-high-warning-threshold {
      type common:xfloat;
      units "mW";
      config false;
      // Qualifiers: observed, realtime
      // Dependencies: Valid only if present = true
      // Persistent: N/A
      // Notification: No
      description "Tx power High warning";
    }

    leaf tx-power-low-warning-threshold {
      type common:xfloat;
      units "mW";
      config false;
      // Qualifiers: observed, realtime
      // Dependencies: Valid only if present = true
      // Persistent: N/A
      // Notification: No
      description "Tx power Low warning";
    }


    // Media real time monitor data


    leaf current-temperature {
      type common:xfloat;
      config false;
      // Qualifiers: observed, realtime
      // Dependencies: Valid only if present = true
      // Persistent: N/A
      // Notification: No
      description "Current temperature";
    }

    leaf current-voltage {
      type common:xfloat;
      units "mV";
      config false;
      // Qualifiers: observed, realtime
      // Dependencies: Valid only if present = true
      // Persistent: N/A
      // Notification: No
      description "Current voltage";
    }

    leaf temp-state {
      type media-status;
      config false;
      // Qualifiers: observed, realtime
      // Dependencies: Valid only if present = true
      // Persistent: N/A
      // Notification: Yes
      description "Temperature High/Low alarm/warning state";
    }

    leaf voltage-state {
      type media-status;
      config false;
      // Qualifiers: observed, realtime
      // Dependencies: Valid only if present = true
      // Persistent: N/A
      // Notification: Yes
      description "Voltage High/Low alarm/warning state";
    }

    // Config parameters

    leaf autoneg {
      type boolean;
      default true;
      config true;
      description "Auto Negotiation";
    }

    leaf-list supported-speed {
      type base-if:speed;
      config true;
      description "Interface supported speed list";
    }
    leaf target_wavelength {
      type common:xfloat;
      config true;
      description "Configured wavelength for tunable media";
    }
    description "Attributes of an optical media adapter";
  }


  // Optical media adapter channel grouping - Everything there is to know
  //                                          about an optical media
  //                                          adapter channel

  grouping media-channel {

    leaf state {
      type boolean; //true <=> if channel is enabled
      config true;
      // Qualifiers: observed, realtime
      // Dependencies: Valid only if  media present = true
      // Persistent: N/A
      // Units : N/A
      // Notification: No
      description "Channel state (Enable/Disable)";
    }

    leaf rx-power {
      type common:xfloat;
      units "mW";
      config false;
      // Qualifiers: observed, realtime
      // Dependencies: Valid only if media present = true
      // Persistent: N/A
      // Notification: No
      description "RX power";
    }

    leaf tx-power {
      type common:xfloat;
      units "mW";
      config false;
      // Qualifiers: observed, realtime
      // Dependencies: Valid only if media present = true
      // Persistent: N/A
      // Notification: No
      description "TX power";
    }

    leaf tx-bias-current {
      type common:xfloat;
      units "mA";
      config false;
      // Qualifiers: observed, realtime
      // Dependencies: Valid only if media present = true
      // Persistent: N/A
      // Notification: No
      description "TX Bias Current";
    }

    leaf oper-status {
      type base-cmn:oper-status-type;
      config false;
      // Qualifiers: observed, realtime
      // Dependencies: !present => oper-status == unknown.
      //               admin-status == testing => oper-status == down.
      // Persistent: N/A
      // Notification: Yes; parameters (oper_status)
      description "Operational status";
    }

    leaf rx-loss {
      type boolean;
      config false;
      // Qualifiers: observed, realtime
      // Dependencies: Valid only if present = true
      // Persistent: N/A
      // Notification: Yes
      description "Channel TX loss status";
    }

    leaf tx-loss {
      type boolean;
      config false;
      // Qualifiers: observed, realtime
      // Dependencies: Valid only if present = true
      // Persistent: N/A
      // Notification: Yes
      description "Channel TX loss status";
    }

    leaf tx-fault {
      type boolean;
      config false;
      // Qualifiers: observed, realtime
      // Dependencies: Valid only if present = true
      // Persistent: N/A
      // Notification: Yes
      description "Channel TX fault status";
    }

    leaf tx-disable {
      type boolean;
      config false;
      // Qualifiers: observed, realtime
      // Dependencies: Valid only if present = true
      // Persistent: N/A
      // Notification: Yes
      description "Channel TX disable status";
    }

    leaf rx-power-state {
      type media-status;
      config false;
      // Qualifiers: observed, realtime
      // Dependencies: Valid only if present = true
      // Persistent: N/A
      // Notification: Yes
      description "RX power High/Low alarm/warning state";
    }

    leaf tx-power-state {
      type media-status;
      config false;
      // Qualifiers: observed, realtime
      // Dependencies: Valid only if present = true
      // Persistent: N/A
      // Notification: Yes
      description "TX power High/Low alarm/warning state";
    }

    leaf tx-bias-state {
      type media-status;
      config false;
      // Qualifiers: observed, realtime
      // Dependencies: Valid only if present = true
      // Persistent: N/A
      // Notification: Yes
      description "TX-BIAS High/Low alarm/warning state";
    }

    leaf cdr-enable {
      type boolean;
      config true;
      description "CDR enable/disable";
    }

    // Config parameters

    leaf speed {
      type base-if:speed;
      config true;
      // Qualifiers: observed, realtime
      // Dependencies: Valid only if present = true
      // Persistent: N/A
      // Notification: No
      description "Speed to derive and set LED state";
    }

    leaf autoneg {
      type boolean;
      default true;
      config true;
      description "Auto Negotiation";
    }

    leaf-list supported-speed {
      type base-if:speed;
      config true;
      description "Interface supported speed list";
    }
    description "Attributes of a channel of an optical media adapter";
  }


  // PHY grouping - Everything there is no know about PHYs

  grouping phy {

    leaf admin-status {
      type base-cmn:admin-status-type;
      config true;
      // Qualifiers: observed, realtime, target
      // Dependencies: None
      // Default: up
      // Persistent: Across process restart: Yes
      //             Across kernel restart:  No
      //             Across power cycle:     No
      // Notification: Yes; parameters (admin_status)
      // Notes: Up <=> Polling of PHY enabled, CPS/FUSE requests
      //               satisfied
      //        Down <=> Polling of PHY disabled, CPS/FUSE requests
      //                 rejected
      //        Testing <=> As with down, but also includes others in
      //                    same diag class
      description "Administrative status";
    }

    leaf oper-status {
      type base-cmn:oper-status-type;
      config false;
      // Qualifiers: observed, realtime
      // Dependencies: !present => oper-status == unknown.
      //               admin-status == testing => oper-status == down.
      // Persistent: N/A
      // Notification: Yes; parameters (oper_status)
      description "Operational status";
    }

    leaf fault-type {
      type fault-type;
      config false;
      // Qualifiers: observed, realtime
      // Dependencies: Valid only if oper-status == fail
      // Persistent: N/A
      // Notification: Yes; parameters (fault_type)
      description "Cause of fault";
    }
    description "Attributes of a port PHY";

    // TBD
  }

  // Contains all the attributes of host system
  // Attributes contains info about host system

  grouping host-system {

      leaf booted {
          type boolean;
          description "flag for host system booted successfully";
      }

      leaf software-rev {
          type string {
              length "32";
          }
          description "Host system software revision";
      }

      leaf slot-number {
          type uint16;
          description "host system slot number";
      }

      leaf fabric-id {
          type string {
              length "32";
          }
          description "Host system fabric id ";
      }
      description "Attributes of host system";
  }

  // Contains all the attributes of a comm-dev
  // comm-dev works as communication channel
  // between host(card) and master

  grouping comm-dev {

      leaf comm-msg {
          type string {
              length "4096";
          }
          description "msg between host system and master";
      }

      leaf chassis-service-tag {
          type string {
              length "34";
          }
          description "Chassis service tag";
      }

      leaf comm-dev-firmware-rev {
          type string {
              length "64";
          }
          description "comm-dev firmware revision";
      }

      description "Comm-dev attributes";
  }

}
