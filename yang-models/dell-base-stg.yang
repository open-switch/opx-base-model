module dell-base-stg {

    namespace "http://www.dellemc.com/networking/os10/dell-base-stg";
    prefix "base-stg";

    import dell-base-common {
        prefix "base-cmn";
    }

    organization
        "Dell EMC";

    contact
    "http://www.dell.com/support";

    description
        "A Spanning Tree Group (STG) comprises of one or more VLANs, which share
         the same instance of the Spanning Tree Protocol (STP).
         This model contains a collection of YANG definitions provided by platform
         for managing the STG objects.

         Copyright (c) 2015-2019 by Dell EMC, All rights reserved.";

    revision 2018-08-17{
        description "Fixing pyang IETF errors and adding documentation to the model.";
        reference "Network Platform Abstraction";	
    }

    revision 2014-12-30 {
        description
            "Initial revision";
        reference "Network Platform Abstraction";	
    }

    typedef interface-state {
        type enumeration {
            enum DISABLED {
                value 0;
                description
                    "Indicates STP state of the interface is disabled";
            }
            enum LISTENING {
                value 1;
                description
                    "Indicates STP state of the interface is listening";
            }
            enum LEARNING {
                value 2;
                description
                    "Indicates STP state of the interface is learning";
            }
            enum FORWARDING {
                value 3;
                description
                    "Indicates STP state of the interface is forwarding";
            }
            enum BLOCKING {
                value 4;
                description
                    "Indicates STP state of the interface is blocking";
            }
        }
        description "Enumeration of possible states of the interface.";
    }

    container default-stg{
        // Qualifier : Target

        leaf id{
            type uint32;
            config false;
            description "Default STG instance id";
        }

        leaf state{
            type interface-state;
            description
                "Default STP state of the all interfaces for default STG instance";
        }
        description "Attribute values of the default STG.";
    }


    list entry {
        // Qualifier : Target

        key "id";

        leaf id {
            type uint32;
            description
                "Identifier of the Spanning Tree Group instance";
        }

        leaf switch-id {
            type base-cmn:logical-switch-id;
            status obsolete;
            description
                "Logical Switch to which this STG instance belongs.";
        }

        leaf-list vlan {
            type base-cmn:vlan-id;
            description
                "List of VLANs to be associated with the STG instance";
        }

        list intf {
            key "if";

            choice  if {
                case index {
                    leaf ifindex {
                        type base-cmn:logical-ifindex;
                        description
                            "Interface Index which is unique across switch to identify
                            logical/physical interface";
                    }
                }
                case name {
                    leaf ifname {
                        type string;
                        description
                            "Interface name which is unique across switch to identify
                            logical/physical interface";
                    }
                }
                description "interface identifier";
            }
            leaf state {
                type interface-state;
                description
                    "STP state of the interface";
            }
            description
                "List of interfaces associated with the STP instance.";
        }
        description
            "Spanning Tree Group instance attributes";
    }
}
