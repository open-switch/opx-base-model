module dell-fcoe-mapper {

    namespace "http://www.dell.com/esg/networking/os10/dell-fcoe-mapper";
    prefix "dell-fcoe-mapper";

    import dell-base-common {
        prefix "base-cmn";
    }

    import ietf-yang-types {
        prefix "yang";
    }

    organization
        "Dell Inc";

    contact
        "www.dell.com/support/softwarecontacts";

    description
        "This module contains a collection of YANG definitions for creating fcoe
        map";

    revision 2016-11-21 {
        description "Initial version";
    }

    typedef fcmac_mode {
        type enumeration {
            enum "FPMA_MODE" {
                description
                  "24 bit FC DID will be prefixed with 24 bit address
                         configured on fcoe-map for generating mac address";
                value 1;
            }
            enum "NULL_MODE" {
                description "The mac address will be zero";
                value 2;
            }
            enum "USER_MODE" {
                description "The mac address will be configured by the user";
                value 3;
            }
         }
    }

    list entry {
        key "mapper-id";

        description "FCoE mapper object attributes";

        leaf mapper-id {
            type base-cmn:base-obj-id-type;
            description "Unique FCoE mapper ID generated or passed upon Create request.
                         Subsequent Modify and Delete request requires
                         this  ID to be passed";
        }

        leaf src_mac_mode {
             type fcmac_mode;
             description "Specifies how source MAC address is to be formed";

        }

        leaf src_map-prefix {
            type uint32;
            description "Fiber channel mapper prefix for source address";
        }

        leaf ingress-src-mac {
            type yang:phys-address;
            description
             "Source MAC provided by user and depends on the mac_mode configured";
        }

        leaf dest_mac_mode {
             type fcmac_mode;
             description "Specifies how destination MAC address is to be formed";

        }

        leaf dest_map-prefix {
            type uint32;
            description "Fiber channel mapper prefix for destination address";
        }

        leaf ingress-dest-mac {
            type yang:phys-address;
            description
             "Ingress destination MAC for mapper";
        }

        leaf fcoe_pkt_vlanid {
            type base-cmn:vlan-id;
            description
             "FCoE packet vlan-id";
        }

        leaf tag_protocol_id {
            type uint16;
            description
             "Tag Protocol id for FCoE packet";
        }

        leaf priority {
            type base-cmn:dot1p;
            description
             " Default priority for vlan tag";
        }

        leaf vft_header {
            type uint32;
            description
             "Virtual Fabric Tagging ID or header";
        }

    }
}
