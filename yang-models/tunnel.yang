module tunnel {

    namespace "http://www.dellemc.com/networking/os10/tunnel";
    prefix "tunnel";

    import dell-base-common {
        prefix "base-cmn";
    }

    import ietf-interfaces {
        prefix "if";
    }

    import dell-base-interface-common {
        prefix "base-if-cmn";
    }

    organization "Dell EMC";
    contact "http://www.dell.com/support";

    description "This module defines the configuration data and operational
                 state data for managing tunnels in the system.

                 Copyright (c) 2015-2019 by Dell EMC, All rights reserved.";

    revision "2018-08-17" {
        description "Fixing pyang IETF errors and adding documentiation to the model.";
        reference "Network Platform Abstraction";	
    }

     revision "2018-03-22" {
        description "Added a remote procedure call clear-tunnel-stats to clear the
                     statistics for a tunnel configured in the system. ";
        reference "Network Platform Abstraction";
    }

    revision "2018-03-07" {
        description "Initial version.";
        reference "Network Platform Abstraction";
    }

    typedef tunnel-type {

        type enumeration {
            enum ip-in-ip {
                description
                "IPv4-in-IPv4 tunnel interface.";
            }

            enum ip-in-ip-gre {
                description
                "IPv4-in-IPv4 with GRE tunnel interface.";
            }

            enum vxlan {
                description
                 "VxLAN tunnel interface.";
            }

            enum mpls{
                description
                "Mutli-Protocol Label Switching tunnel interface";
            }

        }
        description
        "Indicate the type of the tunnel";
    }


    grouping tunnel-entry {

        leaf name {
            type string;
            description
            "Name of the tunnel.";
        }

        leaf type {
            type tunnel-type;
            description
            "Type of the tunnel";
        }

        container local-ip{
            uses base-cmn:ip;
            description
            "IP address of the local tunnel end";
        }

        container remote-ip{
            uses base-cmn:ip;
            description
            "IP address of the remote tunnel end";
        }
        description
        "Specify the tunnel entry attributes";

    }

    container tunnel-state{
        config false;

        list tunnels{
            key "local-ip remote-ip";
            uses tunnel-entry;
            description
            "Operational state data of configured tunnel";
        }
        description
            "State information of the list of currently configured tunnels";
    }

    container tunnel-stats {
        config false;

        list tunnels{
            key "local-ip remote-ip";
            uses tunnel-entry;
            uses base-if-cmn:stats;
            description
            "Operational state data of configured tunnel";
        }
        description
            "Various statistics of the list of currently configured tunnels";
    }

    rpc clear-tunnel-stats{
        description
            "Remote Procedure Call to clear the statistics for a tunnel,
             which is a combination of source and destination IP address.
             This procedure will clear the statistics from the switch so it
             should be used carefully. If a tunnel does not exsist it will
             have no impact.";

        // ATTRIBUTE PATH  : tunnel/clear-tunnel-stats
        // ==============
        //
        // INPUT           : tunnel/clear-tunnel-stats/input/local-ip  (addr-family, address and anything else in bace-cmn:ip)
        // =====             tunnel/clear-tunnel-stats/input/remote-ip (addr-family, address and anything else in bace-cmn:ip)
        //
        // OUTPUT          : None
        // ======

        input {

            container local-ip{
                uses base-cmn:ip;
                description
                "IP address of the local tunnel end. This can be IPv4/IPv6 address
                 with the address family";

                  // C literal   : TUNNEL_CLEAR_TUNNEL_STATS_INPUT_LOCAL_IP_ADDR_FAMILY
                  // Python path : tunnel/clear-tunnel-stats/input/local-ip/addr-family

                  // C literal   : TUNNEL_CLEAR_TUNNEL_STATS_INPUT_LOCAL_IP_ADDR
                  // Python path : tunnel/clear-tunnel-stats/input/local-ip/addr
            }

            container remote-ip{
                uses base-cmn:ip;
                description
                "IP address of the remote tunnel end. This can be IPv4/IPv6 address
                 with the address family";

                  // C literal   : TUNNEL_CLEAR_TUNNEL_STATS_INPUT_REMOTE_IP_ADDR_FAMILY
                  // Python path : tunnel/clear-tunnel-stats/input/remote-ip/addr-family

                  // C literal   : TUNNEL_CLEAR_TUNNEL_STATS_INPUT_REMOTE_IP_ADDR
                  // Python path : tunnel/clear-tunnel-stats/input/remote-ip/addr
            }
        }
     }
 }
