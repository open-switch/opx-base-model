module dell-base-if-linux {
    namespace "http://www.dellemc.com/networking/os10/dell-base-if-linux";

    prefix "base-if-linux";

	import ietf-interfaces {
		prefix "if";
	}
	
    import dell-base-common {
        prefix "base-cmn";
    }

    organization "Dell EMC";
    contact "http://www.dell.com/support";

    description "This model augments the standard interface object(s) and adds
                 specific attributes and/or RPC for linux interfaces.

                 Copyright (c) 2015-2019 by Dell EMC, All rights reserved.";

    revision "2018-12-05" {
        description "Added the member interface index attribute for the bridge interface.";
        reference "Network Platform Abstraction";
    }

    revision "2018-08-10" {
        description "Fixing pyang IETF errors and adding documentation to the model.";
        reference "Network Platform Abstraction";
    }

    revision "2016-01-22" {
        description "Initial version.";
        reference "Network Platform Abstraction";
    }
	
    augment "/if:interfaces/if:interface" {
		
        leaf if-index {
            type base-cmn:logical-ifindex;
            description "Unique identifying number that is used for identifying a physical or logical interface." ;
        }
		leaf if-flags {
			type uint32;
			description "Interface specific flags. These are private and reserved.";
		}
		leaf if-master {
			type uint32;
			description "The if-index of the master for this specific interface";
		}
		leaf dell-type {
			type base-cmn:interface-type;
			description "The interface type as per Dell categorization.";
		}
        leaf mbr-ifindex {
            type base-cmn:logical-ifindex;
            description "The interface index of the member for this specific interface";
        }
	description "Augmenting the standard interface node to include additional attributes.";
    }	
}
