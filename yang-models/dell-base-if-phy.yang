module dell-base-if-phy {
    namespace "http://www.dellemc.com/networking/os10/dell-base-if-phy";

    prefix "base-if-phy";

	import ietf-interfaces {
		prefix "if";
	}
	
    import dell-base-common {
        prefix "base-cmn";
    }

	import dell-base-interface-common {
		prefix "base-if";
	}

    import dell-base-platform-common {
       prefix "platform";
    }
    	
    organization "Dell EMC";
    contact "http://www.dell.com/support";


    description "This model augments the standard interface object(s) and adds
                 specific attributes and/or RPC for physical interfaces.

                 Copyright (c) 2015-2019 by Dell EMC, All rights reserved.";

    revision "2019-03-06" {
        description "Add MAC learning mode HW disable only.";
        reference "Network Platform Abstraction";
    }

    revision "2019-02-22" {
        description "Adding 8x1 breakout mode for front panel port.";
        reference "Network Platform Abstraction";
    }

    revision "2019-01-23" {
        description "Add profile-type attribute in front-panel-port list.";
        reference "Network Platform Abstraction";
    }

    revision "2019-01-18" {
        description "Add port-group attribute in front-panel-port list to display the port-group the front-panel-port is part of.";
        reference "Network Platform Abstraction";
    }

    revision "2018-08-10" {
        description "Fixing pyang IETF errors and adding documentation to the model.";
        reference "Network Platform Abstraction";
    }

    revision "2017-09-27" {
        description "Add per interface supported auto-negotiation attribute.";
        reference "Network Platform Abstraction";
    }

    revision "2016-01-01" {
        description "Initial version.";
        reference "Network Platform Abstraction";
    }

    typedef breakout-mode {
		type enumeration {
			enum DISABLED {
                          value 1;
                        }
		 	enum BREAKOUT_4x1 {
                          value 2;
                        }
		 	enum BREAKOUT_2x1 {
                          value 3;
                        }
		 	enum BREAKOUT_1x1 {
                          value 4;
                        }
		 	enum BREAKOUT_8x1 {
                          value 5;
                        }
		}
                description "Enumeration of all possible values of breakout modes";
    }

    typedef mac-learn-mode{

        type enumeration{

            enum DROP{
              value 1;
                description "Drop packets with unkown source mac address in both OS and HW. Do not learn, Do not forward";
            }

            enum DISABLE{
              value 2;
                description "Do not learn new source MAC in both OS and HW. Forward Based on destination MAC";
            }

            enum HW{
              value 3;
                description "OS and Hardware Learning. Learn source MAC. Forward based on destination";
            }

            enum CPU_TRAP{
              value 4;
                description "Trap packets with unknown source MAC to CPU from HW. Do not learn.
                    Do not forward.";
            }

            enum CPU_LOG{
              value 5;
                description "Trap packets with unknown source MAC to CPU from HW. Do not learn.
                    Forward based on destination MAC.";
            }

            enum HW_DISABLE_ONLY{
                value 6;
                description "Do not learn new source MAC address only in the HW.";
            }

        }
        description "Enumeration of all possible MAC-learning modes that can be configured on the interface.";
    }	
	

    list front-panel-port {
        key "front-panel-port";

        //QUALIFIER : Target

        leaf front-panel-port {
            type uint32;
            description "ID of the front panel port (indexed from 1 to max front panel port)";
        }

        leaf npu-id {
            type base-cmn:npu-id;
            description "The npu that owns the port";
        }

        leaf media-id {
            type uint32;
            description "The media ID of the port - use this to check the corresponding PAS object to get
            	the acutal media details";
        }

        leaf-list port {
        	type base-cmn:npu-port-id;
        	description "This list contains all the hardware ports this fron-panel port contains.
                             Look up the details on the lane in the npu-port-lane object";
        }

        leaf control-port {
        	type base-cmn:npu-port-id;
        	description "Use this port for significant operations";
        }

        leaf default-name {
        	type string;
        	description "This is the default name of the port.";
        }

        leaf port-group {
            type string;
            description "Name of the port-group the port is part of";
        }

        leaf profile-type {
            type string;
            description "Profile type of the port";
        }

        leaf mac-offset {
            type uint32;
            description "Offset from system base MAC Address. MAC address of the port is calculated by adding mac_offset with the base MAC address";
        }	

        leaf phy-mode {
            type base-if:phy-mode-type;
            description "PHY mode of the port(Ethernet or FC)";
        }

	leaf breakout-mode {
	    type base-cmn:breakout-type;
       	    config false;
            description "Breakout mode of the front panel port";
	}
        leaf port-speed {
            type base-if:speed;
            description "port speed of the front panel port";
        }

        leaf default-phy-mode {
            type base-if:phy-mode-type;
            config false;
            description "Default Port PHY mode (Ethernet or FC)";
        }

        leaf default-breakout-mode {
            type base-cmn:breakout-type;
            config false;
            description "Default platform breakout mode for the port";
        }

        leaf default-port-speed {
            type base-if:speed;
            config false;
            description "Default speed of the port";
        }
		
        uses base-if:breakout-capabilities;

        description "List of all front-panel ports, uniquely identified with the key 'front-panel-port'.
                     Each item in the list contain various attributes of the front-panel port, including the NPU ID it belongs to.";
    }
		
    list hardware-port {
        key "npu-id hw-port";

        //QUALIFIER : Target

        leaf npu-id {
            type uint32;
            description "NPU id ";
        }
        leaf hw-port {
            type uint32;
            description "The hardware port id.";
        }

        leaf hw-control-port {
            type uint32;
            description "The hardware port that is the master.  Normally one hardware port
                         will be designated as a master port. This port is used to change the breakout
                         configuration of any front-panel port member.";
        }

        leaf subport-id {
            type uint32;
            description "The physical lane on which this hardware port exists.";
        }

	leaf front-panel-port {
	    type uint32;
            description "The front-panel port that this hardware port is a member of.";
	}
		
	leaf fanout-mode {
	    type breakout-mode;
	    config false;
            description "The breakout-mode value";
	}

        description "List of all hardware ports, uniquely identified with the key-pair 'npu-id, hw-port'.
                     This list associates a hardware port to the front-panel port and the NPU it belongs to.
                     This list is not dynamic and therefore it's similar across all the instances of a product.";
    }
	
    list physical {
        key "npu-id port-id";

        //QUALIFIER : Target

        uses base-if:physical-port-address;

        leaf hardware-port-id {
            type base-cmn:npu-port-id;
            status deprecated;
            description "This is the physical hardware port";
        }

        leaf-list hardware-port-list {
            type base-cmn:npu-port-id;
            description "A sub-list of all the npu port(s) this physical port contains";
        }

        leaf phy-mode {
            type base-if:phy-mode-type;
            description "Port PHY mode (Ethernet or FC)";
        }

        leaf speed {
            type base-if:speed;
            description "Current max configured speed of physical port";
        }

	leaf front-panel-number {
	    type uint32;
            description "Front panel port this physical port is part of.
                         This leaf is deprecated.";
	}
		
        leaf-list breakout-capabilities {
	    type breakout-mode ;
            status deprecated;
            description "Breakout capabilities of this port.";
	}
		
	leaf fanout-mode {
	    type breakout-mode;
	    config false;
            status deprecated;
            description "Fanout capabilities of this port.";
	}
		
        leaf phy-media {
            type platform:media-type;
            description "Physical media type ";
        }
						
        leaf loopback {
            type base-cmn:loopback-type;
            description "Loopback type(phy/mac), in case it is a loopback interface;
                         otherwise set to 'none'";
        }

        leaf-list supported-speed {
            type base-if:speed;
            description "sub-list of all supported interface speeds";
        }
        description "List of all physical ports, uniquely identified with the key-pair 'npu-id, port-id'.
                     This list associates a physical port to the front-panel port and the NPU it belongs to.
                     This list includes attributes specific for physical intefaces.";
    }
	
    augment "/if:interfaces/if:interface" {
		uses base-if:physical-port-address;
		
        leaf phy-media {
            type platform:media-type;
            description "Physical media type ";
        }

        leaf hw-profile {
            type uint32;
            description "Hardware profile ID specific to the physical port. It is a platform specific property.
                         It depends on the port configuration and the media-type present in the port.";
        }

        leaf loopback {
            type base-cmn:loopback-type;
            description "loopback type(phy/mac) if it is a loopback interface; otherwise set to 'none'";
        }

        leaf identification-led {
            type boolean;
            description "LED state to set OFF(0) / ON (1)";
        }
        	
        uses base-if:mac-learn-limit;

        leaf learn-mode{
            type mac-learn-mode;
            description "MAC-learning mode this interface is configured for";
        }

        leaf tagging-mode {
        	type enumeration {
        		enum UNTAGGED {
                          value 1;
        			description "port accepts untagged packets only.";
        		}
        		enum TAGGED {
                          value 2;
        			description "port accepts tagged packets only.";
        		}
        		enum HYBRID {
                          value 3;
        			description "port accepts both untagged and tagged packets.";
        		}
        	}
                description "Enumeration of all possible types of packets(tagged/un-tagged/hybrid) this interface can accept";
        }

        leaf supported-autoneg {
            type base-if:supported-autoneg;
            description "Supported auto-negotiation value for the interface.";
        }
        description "Extending standard interface object to include attributes specific to a physical interface";
   }		
	rpc breakout {

		description "This method allows the change of the breakout mode on a front panel port and
			at the same time will create logical interfaces based on the provided names";

            // QUALIFIER       : Target
            // =========
            //
            // ATTRIBUTE PATH  : base-if-phy/breakout
            // =============
            //
            // INPUT           : base-if-phy/breakout/input/front-panel-port (id of the front-panel port)
            //                   base-if-phy/breakout/input/breakout-mode    (break-out mode to be configured)
            //                   base-if-phy/breakout/input/port-speed       (port-speed to be configured)
            // =====
            //
            // OUTPUT          : None
            // ======

	    input {
	        leaf front-panel-port {
	            type uint32;
	            description "The hardware ports that are owned by the front panel port.";
	        }
	        	
	        leaf breakout-mode {
	       	    type breakout-mode ;
	            description "The breakout mode of the front panel port";
		}	
                leaf port-speed {
                    type base-if:speed;
	            description "The interface speed of the front panel port.";
                }
	    }
	}

	rpc set-breakout-mode {

		description "This RPC just changes the breakout mode on a front panel port object but
					doesn't effect any of the logical interfaces.  The expectation is that
					all logical interfaces are deleted before this operation is executed";
            // QUALIFIER       : Target
            // =========
            //
            // ATTRIBUTE PATH  : base-if-phy/set-breakout-mode
            // =============
            //
            // INPUT           : Attributes from base-if/physical-port-address     (as needed)
            //                   base-if-phy/set-breakout-mode/input/breakout-mode (break-out mode to be configured)
            //                   base-if-phy/set-breakout-mode/input/effected-port (port(s)this new mode is applicable on)
            // =====
            //
            // OUTPUT          : None
            // ======

	    input {
    	    uses base-if:physical-port-address;
	        	
	        leaf breakout-mode {
			type breakout-mode ;
	        	description "this is the new mode to configure.";
		}	

			leaf-list  effected-port {
				type base-cmn:npu-port-id;
            	description "These are the ports that are effected by this change.
            	When breaking out, this should be one port and when breaking in, this should
            	be all of the ports that need to be convered.";			
			}
	    }
	}

}
