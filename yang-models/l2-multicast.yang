module l2-multicast {

    namespace "http://www.dellemc.com/networking/os10/l2-multicast";
    prefix "base-l2-mcast";

    import dell-base-common {
        prefix "base-cmn";
    }

    import ietf-interfaces {
        prefix "if";
    }

    organization "Dell EMC";
    contact "http://www.dell.com/support";

    description "This module contains a collection of YANG definitions
                 for managing L2 multicast. This feature works in conjunction with
                 IGMP/MLD Snooping support.

                 Copyright (c) 2015-2019 by Dell EMC, All rights reserved.";

    revision "2018-08-17" {
        description "Fixing pyang IETF errors and adding documentation to the model.";
        reference "Network Platform Abstraction";
    }

    revision "2017-11-01" {
        description "Initial version.";
        reference "Network Platform Abstraction";
    }

    rpc cleanup-l2mc-member {
        description "Each VLAN has a number of associated multicast groups. Each such group comprises of a list
                     of logical or physical interfaces. This RPC trigers L2-multicast service to remove the given interface
                     from all the multicats groups of the given vlan-id. This RPC is triggered during interface
                     deletion/addition to a LAG master";


        // ATTRIBUTE PATH  : base-l2-mcast/cleanup-l2mc-member
        // ==============
        //
        // QUALIFIER       : Target
        // =========
        //
        // INPUT           : base-l2-mcast/cleanup-l2mc-member/input/ifindex (if-index of the multicast group member to be removed)
        // =====          OR base-l2-mcast/cleanup-l2mc-member/input/ifname  (interface name of the multicast group member to be removed)
        //
        //               AND base-l2-mcast/cleanup-l2mc-member/input/vlan-id (VLAN ID associated with the multicast member-group)
        //
        // OUTPUT          : None
        // ======

        input {
            leaf ifindex {
                type base-cmn:logical-ifindex;
                description "Interface index to identify logical/physical interface for which multicast group
                             member cleanup will be done. If this attribute is not given, ifname must be used
                             as input to identify interface.";
            }
            leaf ifname {
                type if:interface-ref;
                description "Interface name to identify logical/physical interface for which multicast group
                             member cleanup will be done. This attribute is only effective when ifindex is not
                             given.";
            }
            leaf vlan-id {
                type base-cmn:vlan-id;
                description "The VLAN ID for which multicast group member cleanup will be done. If it is not
                             given, cleanup will work on all VLANs for specific interface.";
            }
        }
    }

    container flood-restrict {
        description "The unknown multicast traffic (IPv4/IPv6) are flooded to all VLAN members by default. If
                     flood-restrict is enabled on specific VLAN, the unknown traffic from one port of this VLAN
                     will be forwarded to those links that have active listeners in it (e.g. port connected with
                     L3 multicast router).
                     This container could be used to disable/enable flood-restrict on IPv4 and IPv6 multicast
                     traffic for list of VLANs.";

        list vlan-status {
            key "vlan-id";

            leaf vlan-id {
                type base-cmn:vlan-id;
                description "Specify VLAN for which flooding restrict will be configured.";
            }

            leaf enable {
                type boolean;
                description "Enable or disable flooding restrict for specific VLAN.";
            }

            description "Set flood-restrict status for specific VLAN.";
        }
    }
}
