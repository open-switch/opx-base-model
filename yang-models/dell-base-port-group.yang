module dell-base-port-group {
    namespace "http://www.dellemc.com/networking/os10/dell-base-port-group";
    prefix "base-pg";

    import dell-port-group { prefix "dell-pg"; }

    organization "Dell EMC";
    contact "http://www.dell.com/support";

    description "This model contains Dell EMC specific port-group definition and its attributes
                 This model extends the dell-pg model.

                 Copyright (c) 2015-2019 by Dell EMC, All rights reserved.";

    revision "2018-08-17" {
        description "Fixing pyang IETF errors and adding documentation to the model.";
        reference "Network Platform Abstraction";
    }

    revision "2018-04-05" {
        description "Augmenting hybrid group config and state object.";
        reference "Network Platform Abstraction";
    }

    revision "2016-11-22" {
        description "Initial version.";
        reference "Network Platform Abstraction";
    }

    augment "/dell-pg:port-groups/dell-pg:port-group" {
        description "Extending the port-group list";
    }

    augment "/dell-pg:port-groups/dell-pg:hybrid-group" {
        description "Extending the hybrid-group list";
    }

    augment "/dell-pg:port-groups-state/dell-pg:port-group-state" {
        leaf-list hwport-list {
            type uint32;
            description "List of hardware ports belonging to this port-group";
        }

        leaf-list front-panel-port {
            type uint32;
            description "list of the front panel port Ids associated with this port-group.";
        }
        description "Extending the port-group state object";
    }


    augment "/dell-pg:port-groups-state/dell-pg:hybrid-group-state" {
        leaf-list hwport-list {
            type uint32;
            description "List of hardware ports belonging to this port-group";
        }

        leaf-list front-panel-port {
            type uint32;
            description "list of the front panel port id's associated with this port-group.";
        }
        description "Extending the hybrid-group state object. Hybrid group consists of a
                 group of ports that can be configured with different breakout mode using profiles";
    }

    augment "/dell-pg:port-groups-state/dell-pg:port-group-state/dell-pg:br-cap" {
        description "Extending the breakout capabilities";
    }
}
