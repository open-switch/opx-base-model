module dell-base-if-fc {

    namespace "http://www.dellemc.com/networking/os10/dell-base-if-fc";
    prefix "base-if-fc";

    import ietf-interfaces { prefix "if"; }
    import dell-base-common { prefix "base-cmn"; }
    import ietf-yang-types { prefix "yang"; }
    import iana-if-type { prefix "ianaift"; }

    organization
        "Dell EMC";

    contact
        "http://www.dell.com/support";

    description
        "Fibre Channel over Ethernet (FCoE) encapsulates Fibre channel frames over Ethernet networks.
         FC-MAP identifies which fabric the FCoE switch belongs to.

         This model contains a collection of YANG definitions for fcoe-map configurations.

         Copyright (c) 2015-2019 by Dell EMC, All rights reserved.";

    revision 2018-04-12 {
        description "Fixing pyang IETF errors and adding documentiation to the model.";
        reference "Network Platform Abstraction";
    }

    revision 2016-11-21 {
        description "Initial version";
        reference "Network Platform Abstraction";
    }

    typedef fcmac-mode {
        type enumeration {
            enum "FPMA_MODE" {
                value 1;
                description "In this mode, the 48 Bits MAC address is built by appending the FC_ID to a
			     24-bit the FCoE MAC address prefix (FC-MAP).";
            }
            enum "NULL_MODE" {
                value 2;
                description "In this mode, The MAC address will be set to zero";
            }
            enum "USER_MODE" {
                value 3;
                description "In this mode, The MAC address will be specified by the user";
            }
         }
        description "Enumeration of all values for the FC MAC address modes";
    }

    augment "/if:interfaces/if:interface" {
        when "if:type = 'ianaift:fibreChannel'";

        leaf bb-credit {
          type uint32;
          description "The Buffer-to-Buffer Credit allocation";
        }
        leaf bb-credit-recovery {
          type uint32;
          description "The Buffer-to-Buffer Credit Recovery";
        }

        leaf src-mac-mode {
             type fcmac-mode;
             description "Specifies how source MAC address is to be formed";
        }

        leaf src-map-prefix {
            type uint32;
            description "Fiber channel mapper prefix for source address";
        }

        leaf ingress-src-mac {
            type yang:phys-address;
            description
             "Source MAC provided by user and depends on the mac_mode configured";
        }

        leaf dest-mac-mode {
             type fcmac-mode;
             description "Specifies how destination MAC address is to be formed";

        }

        leaf dest-map-prefix {
            type uint32;
            description "Fiber channel mapper prefix for destination address";
        }

        leaf ingress-dest-mac {
            type yang:phys-address;
            description
             "Ingress destination MAC for mapper";
        }

        leaf fcoe-pkt-vlanid {
            type base-cmn:vlan-id;
            description
             "FCoE packet vlan-id";
        }

        leaf tag-protocol-id {
            type uint16;
            description
             "Tag Protocol id for FCoE packet";
        }

        leaf priority {
            type base-cmn:dot1p;
            description
             " Default priority for vlan tag";
        }

        leaf vft-header {
            type uint32;
            description
             "Virtual Fabric Tagging ID or header";
        }

        leaf mtu {
            type uint32;
            description
             "FC port MTU";
        }

        leaf flow-control-enable {
            type boolean;
            description
             "Flow control mode";
        }

        description "Attributes of a FCoE interface";
    }
    augment "/if:interfaces-state/if:interface" {
        leaf bb-credit-receive {
            type uint32;
            description " Buffer-to-Buffer Credit Receive";
        }
        description "Attributes of a FCoE interface state";
    }
}
