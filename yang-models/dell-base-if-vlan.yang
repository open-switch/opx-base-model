module dell-base-if-vlan {
    namespace "http://www.dellemc.com/networking/os10/dell-base-if-vlan";

    prefix "base-if-vlan";

    import ietf-interfaces {
        prefix "if";
    }
    import ietf-yang-types {
        prefix "yang";
    }
	
    import dell-base-common {
        prefix "base-cmn";
    }

    organization "Dell EMC";
    contact "http://www.dell.com/support";


    description "This model augments the standard interface object(s) and adds
                 specific attributes and/or RPC for VLAN interfaces.

                 Copyright (c) 2015-2019 by Dell EMC, All rights reserved.";

    revision "2018-08-10" {
        description "Fixing pyang IETF errors and adding documentation to the model.";
        reference "Network Platform Abstraction";
    }

    revision "2016-01-01" {
        description "Initial version.";
        reference "Network Platform Abstraction";
    }
	
    augment "/if:interfaces/if:interface" {
        when "if:type = 'ianaift:l2vlan' or if:type = 'ianaift:l3vlan'";

        leaf id {
            type base-cmn:vlan-id;
            description "the VLAN id associated with the interface";
        }	
        description "Adding VLAN specific attributes to the interface object";
    }
}
