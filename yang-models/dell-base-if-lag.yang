module dell-base-if-lag {
    namespace "http://www.dellemc.com/networking/os10/dell-base-if-lag";

    prefix "base-if-lag";

	import ietf-interfaces {
		prefix "if";
	}
	
    import dell-base-common {
        prefix "base-cmn";
    }

    import dell-base-if-phy {
        prefix "base-if-phy";
    }

    organization "Dell EMC";
    contact "http://www.dell.com/support";

    description "This model augments the standard interface and adds Dell EMC specific
                 There is no separate object registered for this model.
                 All the LAG specific attributes are referenced through the dell-base-if-cmn object.

                 Copyright (c) 2015-2019 by Dell EMC, All rights reserved.";

    revision "2018-04-12" {
        description "Fixing pyang IETF errors and adding documentiation to the model.";
        reference "Network Platform Abstraction";
    }

    revision "2016-01-01" {
        description "Initial version.";
        reference "Network Platform Abstraction";
    }
	
    augment "/if:interfaces-state/if:interface" {
	when "if:type = 'ianaift:ieee8023adLag'";
        leaf num-ports {
            type uint32;
            description "number of members in the LAG interface";
        }	
        description "Extending the state attributes of LAG interface";
    }
	
    augment "/if:interfaces/if:interface" {
	when "if:type = 'ianaift:ieee8023adLag'";
        leaf id {
            type uint32;
            description "Lag id from Applications";
        }


        leaf lag-opaque-data {
            type base-cmn:lag-opaque-data;
            config false;
            description
                "NPU LAG opaque data associated with the LAG module";
        }

        leaf lag-port-state {
            type enumeration {
                enum DISABLE;
                enum ENABLE;
            }
            description "state of member port in LAG to hash traffic
                disable or enable";
        }

        leaf-list block-port-list {
            type if:interface-ref;
            description "Port list to block in NPU";
        }

        leaf-list unblock-port-list {
            type if:interface-ref;
            description "Port list to unblock in NPU";
        }

        leaf learn-mode{
            type base-if-phy:mac-learn-mode;
            description "Mode in which mac adresses are learned on this interface";
        }
	description "Extend the interface object with LAG attributes.";
    }
}
