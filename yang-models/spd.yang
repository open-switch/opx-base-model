module spd {
    namespace "http://www.dellemc.com/networking/os10/spd";
    prefix "spd";

    import ietf-ipsec {
        prefix "eipsec";
    }
    import ietf-inet-types {
        prefix "inet";
    }
    import ietf-interfaces {
        prefix "if";
    }


    organization "Dell EMC";
    contact "http://www.dell.com/support";

    description "This model Security Policy Database (SPD) augments IETF IPsec and
                 adds security association grouping to policy database.

                 Copyright (c) 2015-2019 by Dell EMC, All rights reserved.";

    revision 2018-08-17{
        description "Fixing pyang IETF errors and adding documentiation to the model.";
        reference "Network Platform Abstraction";	
    }

    revision "2018-08-02" {
        description "Adding VRF name into the spd-entries.";
        reference "Network Platform Abstraction";	
    }

    revision "2017-08-18" {
        description "Initial version.";
        reference "Network Platform Abstraction";	
    }

    typedef ipsec-level {

        type enumeration {
            enum REQUIRED {
                value 1;
                description "drop the packet and acquire SA";
            }
            enum USE {
                value 2;
                description "do not drop the packet and do not acquire SA";
            }
        }
        description "Different IPSec levels indicating action to be taken when SAs for the policy is not found.";
    }

    deviation "/eipsec:ipsec/eipsec:sad/eipsec:sad-entries/eipsec:ah/eipsec:authentication-algorithm/eipsec:hmac-sha1-96/eipsec:key-str" {
        deviate replace {
            type string;
        }
    }

    grouping ip-prefix {

        leaf source-ip-address {
            type inet:ip-prefix;
            description "Source Interface ip prefix.";
        }

        leaf destination-ip-address {
            type inet:ip-prefix;
            description "Destination Interface ip prefix.";
        }
        description "This grouping provides ip-prefix represenation for source and destination ip addresses.";
    }

    augment "/eipsec:ipsec/eipsec:spd/eipsec:spd-entries" {

        uses eipsec:ipsec-sa-grouping;

        uses ip-prefix;

        leaf ifname {
            type if:interface-ref;
            description "Network interface on which the policy is applied.";
        }

        leaf policy-level {
            type ipsec-level;
            description "IPSec policy level.";
        }

        leaf priority {
            type uint32;
            default 0;
            description "Priority Value for the policy.";
        }

        leaf vrf-name {
            type string;
            description "Network instance (VRF) name.";
        }
        description "The following grouping will be used to configure security policy database";

    }

     augment "/eipsec:spd/eipsec:spd-entries" {

        uses ip-prefix;
        leaf ifname {
            type if:interface-state-ref;
            description "Network interface on which the policy is applied.";
        }

        leaf priority {
            type uint32;
            description "Priority Value for the policy.";
        }
        description "The following grouping will be used to get security policy database information";

     }
}
