module ietf-access-control-list {
    namespace "urn:ietf:params:xml:ns:yang:ietf-access-control-list";
    prefix acl;
    import ietf-yang-types {
        prefix yang;
    }
    import ietf-packet-fields {
        prefix packet-fields;
    }
    organization
        "IETF NETMOD (NETCONF Data Modeling Language)
        Working Group";

    contact
        "WG Web: http://tools.ietf.org/wg/netmod/
        WG List: netmod@ietf.org
        Editor: Dean Bogdanovic
        ivandean@gmail.com
        Editor: Mahesh Jethanandani
        mjethanandani@gmail.com
        Editor: Lisa Huang
        lyihuang16@gmail.com
        Editor: Sonal Agarwal
        agarwaso@cisco.com
        Editor: Dana Blair
        dblair@cisco.com";

    description
        "This YANG module defines a component that describing the
        configuration of Access Control Lists (ACLs).
        Copyright (c) 2016 IETF Trust and the persons identified as
        the document authors.  All rights reserved.
        Redistribution and use in source and binary forms, with or
        without modification, is permitted pursuant to, and subject
        to the license terms contained in, the Simplified BSD
        License set forth in Section 4.c of the IETF Trust's Legal
        Provisions Relating to IETF Documents
        (http://trustee.ietf.org/license-info).
        This version of this YANG module is part of RFC XXXX; see
        the RFC itself for full legal notices.";

    revision 2017-06-16 {
        description
            "Added feature and identity statements for different types
            of rule matches. Split the matching rules based on the
            feature statement and added a must statement within
            each container.";
        reference
            "RFC XXX: Network Access Control List (ACL) YANG Data Model.";
    }

    revision 2016-10-12 {
        description
            "Base model for Network Access Control List (ACL).";
        reference
            "RFC XXXX: Network Access Control List (ACL)
            YANG Data  Model";
    }
    /* Draft version taken from: https://tools.ietf.org/html/draft-ietf-netmod-acl-model-11 */

    /*
     * Identities
     */
    identity acl-base {
        description
            "Base Access Control List type for all Access Control List type
            identifiers.";
    }

    identity ipv4-acl {
        base acl:acl-base;
        description
            "ACL that primarily matches on fields from the IPv4 header
            (e.g. IPv4 destination address) and layer 4 headers (e.g. TCP
                    destination port).  An acl of type ipv4-acl does not contain
            matches on fields in the ethernet header or the IPv6 header.";
    }

    identity ipv6-acl {
        base acl:acl-base;
        description
            "ACL that primarily matches on fields from the IPv6 header
            (e.g. IPv6 destination address) and layer 4 headers (e.g. TCP
                    destination port). An acl of type ipv6-acl does not contain
            matches on fields in the ethernet header or the IPv4 header.";
    }

    identity eth-acl {
        base acl:acl-base;
        description
            "ACL that primarily matches on fields in the ethernet header,
            like 10/100/1000baseT or WiFi Access Control List. An acl of
                type eth-acl does not contain matches on fields in the IPv4
                header, IPv6 header or layer 4 headers.";
    }

    identity mixed-l2-l3-ipv4-acl {
        base "acl:acl-base";

        description
            "ACL that contains a mix of entries that
            primarily match on fields in ethernet headers,
                      entries that primarily match on IPv4 headers.
                          Matching on layer 4 header fields may also exist in the
                          list.";
    }

    identity mixed-l2-l3-ipv6-acl {
        base "acl:acl-base";

        description
            "ACL that contains a mix of entries that
            primarily match on fields in ethernet headers, entries
            that primarily match on fields in IPv6 headers. Matching on
            layer 4 header fields may also exist in the list.";
    }

    identity mixed-l2-l3-ipv4-ipv6-acl {
        base "acl:acl-base";

        description
            "ACL that contains a mix of entries that
            primarily match on fields in ethernet headers, entries
            that primarily match on fields in IPv4 headers, and entries
            that primarily match on fields in IPv6 headers. Matching on
            layer 4 header fields may also exist in the list.";
    }

    identity any-acl {
        base "acl:acl-base";

        description
            "ACL that can contain any pattern to match upon";
    }

    /*
     * Features
     */
    feature l2-acl {
        description
            "Layer 2 ACL supported";
    }

    feature ipv4-acl {
        description
            "Layer 3 IPv4 ACL supported";
    }

    feature ipv6-acl {
        description
            "Layer 3 IPv6 ACL supported";
    }

    feature mixed-ipv4-acl {
        description
            "Layer 2 and Layer 3 IPv4 ACL supported";
    }

    feature mixed-ipv6-acl {
        description
            "Layer 2 and Layer 3 IPv6 ACL supported";
    }

    feature l2-l3-ipv4-ipv6-acl {
        description
            "Layer 2 and any Layer 3 ACL supported.";
    }

    feature tcp-acl {
        description
            "TCP header ACL supported.";
    }

    feature udp-acl {
        description
            "UDP header ACL supported.";
    }

    feature icmp-acl {
        description
            "ICMP header ACL supported.";
    }

    feature any-acl {
        description
            "ACL for any pattern.";
    }

    /*
     * Typedefs
     */
    typedef acl-type {
        type identityref {
            base acl-base;
        }
        description
            "This type is used to refer to an Access Control List
            (ACL) type";
    }

    typedef access-control-list-ref {
        type leafref {
            path "/access-lists/acl/acl-name";
        }
        description
            "This type is used by data models that need to reference an
            Access Control List";
    }

    /*
     * Configuration data nodes
     */
    container access-lists {
        description
            "This is a top level container for Access Control Lists.
            It can have one or more Access Control Lists.";
        list acl {
            key "acl-type acl-name";
            description
                "An Access Control List(ACL) is an ordered list of
                Access List Entries (ACE). Each Access Control Entry has a
                list of match criteria and a list of actions.
                Since there are several kinds of Access Control Lists
                implemented with different attributes for
                different vendors, this
                model accommodates customizing Access Control Lists for
                each kind and for each vendor.";
            leaf acl-name {
                type string;
                description
                    "The name of access-list. A device MAY restrict the length
                    and value of this name, possibly space and special
                    characters are not allowed.";
            }
            leaf acl-type {
                type acl-type;
                description
                    "Type of access control list. Indicates the primary intended
                    type of match criteria (e.g. ethernet, IPv4, IPv6, mixed,
                            etc) used in the list instance.";
            }
            container acl-oper-data {
                config false;
                description
                    "Overall Access Control List operational data";
            }
            container access-list-entries {
                description
                    "The access-list-entries container contains
                    a list of access-list-entries(ACE).";
                list ace {
                    key "rule-name";
                    ordered-by user;
                    description
                        "List of access list entries(ACE)";
                    leaf rule-name {
                        type string;
                        description
                            "A unique name identifying this Access List
                            Entry(ACE).";
                    }

                    container matches {
                        description
                            "The rules in this set determine what fields will be
                            matched upon before any action is taken on them.
                            The rules are selected based on the feature set
                            defined by the server and the acl-type defined.";

                        container l2-acl {
                            if-feature l2-acl;
                            must "../../../../acl-type = 'eth-acl'";
                            uses packet-fields:acl-eth-header-fields;
                            description
                                "Rule set for L2 ACL.";
                        }

                        container ipv4-acl {
                            if-feature ipv4-acl;
                            must "../../../../acl-type = 'ipv4-acl'";
                            uses packet-fields:acl-ip-header-fields;
                            uses packet-fields:acl-ipv4-header-fields;
                            description
                                "Rule set that supports IPv4 headers.";
                        }

                        container ipv6-acl {
                            if-feature ipv6-acl;
                            must "../../../../acl-type = 'ipv6-acl'";
                            uses packet-fields:acl-ip-header-fields;
                            uses packet-fields:acl-ipv6-header-fields;
                            description
                                "Rule set that supports IPv6 headers.";
                        }

                        container l2-l3-ipv4-acl {
                            if-feature mixed-ipv4-acl;
                            must "../../../../acl-type = 'mixed-l2-l3-ipv4-acl'";
                            uses packet-fields:acl-eth-header-fields;
                            uses packet-fields:acl-ip-header-fields;
                            uses packet-fields:acl-ipv4-header-fields;
                            description
                                "Rule set that is a logical AND (&&) of l2
                                and ipv4 headers.";
                        }

                        container l2-l3-ipv6-acl {
                            if-feature mixed-ipv6-acl;
                            must "../../../../acl-type = 'mixed-l2-l3-ipv6-acl'";
                            uses packet-fields:acl-eth-header-fields;
                            uses packet-fields:acl-ip-header-fields;
                            uses packet-fields:acl-ipv6-header-fields;
                            description
                                "Rule set that is a logical AND (&&) of L2
                                && IPv6 headers.";
                        }

                        container l2-l3-ipv4-ipv6-acl {
                            if-feature l2-l3-ipv4-ipv6-acl;
                            must "../../../../acl-type = 'mixed-l2-l3-ipv4-ipv6-acl'";
                            uses packet-fields:acl-eth-header-fields;
                            uses packet-fields:acl-ip-header-fields;
                            uses packet-fields:acl-ipv4-header-fields;
                            uses packet-fields:acl-ipv6-header-fields;
                            description
                                "Rule set that is a logical AND (&&) of L2
                                && IPv4 && IPv6 headers.";
                        }

                        container tcp-acl {
                            if-feature tcp-acl;
                            uses packet-fields:acl-tcp-header-fields;
                            description
                                "Rule set that defines TCP headers.";
                        }

                        container udp-acl {
                            if-feature udp-acl;
                            uses packet-fields:acl-udp-header-fields;
                            description
                                "Rule set that defines UDP headers.";
                        }

                        container icmp-acl {
                            if-feature icmp-acl;
                            uses packet-fields:acl-icmp-header-fields;
                            description
                                "Rule set that defines ICMP headers.";
                        }

                        container any-acl {
                            if-feature any-acl;
                            must "../../../../acl-type = 'any-acl'";
                            presence "Matches any";
                            description
                                "Rule set that allows for a any ACL.";
                        }
                    }

                    container actions {
                        description
                            "Definitions of action criteria for this Access List
                            Entry.";
                        choice packet-handling {
                            default "deny";
                            description
                                "Packet handling action.";
                            case deny {
                                leaf deny {
                                    type empty;
                                    description
                                        "Deny action.";
                                }
                            }
                            case permit {
                                leaf permit {
                                    type empty;
                                    description
                                        "Permit action.";
                                }
                            }
                        }
                        leaf logging {
                            type boolean;
                            description
                                "Log the rule on which the match occurred.
                                Setting the value to true enables logging,
                                        whereas setting the value to false disables it.";
                        }
                    }
                    /*
                     * Operational state data nodes
                     */
                    container ace-oper-data {
                        config false;
                        description
                            "Operational data for this Access List Entry.";
                        leaf match-counter {
                            type yang:counter64;
                            description
                                "Number of matches for this Access List Entry";
                        }
                    }
                }
            }
        }
    }
}
