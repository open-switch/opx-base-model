module ietf-packet-fields {
    namespace "urn:ietf:params:xml:ns:yang:ietf-packet-fields";
    prefix packet-fields;

    import ietf-inet-types {
        prefix inet;
    }

    import ietf-yang-types {
        prefix yang;
    }

    organization
        "IETF NETMOD (NETCONF Data Modeling Language) Working
        Group";

    contact
        "WG Web: http://tools.ietf.org/wg/netmod/
        WG List: netmod@ietf.org

        Editor: Dean Bogdanovic
        ivandean@gmail.com
        Editor: Mahesh Jethanandani
        mahesh@cisco.com
        Editor: Lisa Huang
        lyihuang16@gmail.com
        Editor: Sonal Agarwal
        agarwaso@cisco.com
        Editor: Dana Blair
        dblair@cisco.com";

    description
        "This YANG module defines groupings that are used by
        ietf-access-control-list YANG module. Their usage is not
        limited to ietf-access-control-list and can be
        used anywhere as applicable.
        Copyright (c) 2016 IETF Trust and the persons identified as
        the document authors.  All rights reserved.
        Redistribution and use in source and binary forms, with or
        without modification, is permitted pursuant to, and subject

        to the license terms contained in, the Simplified BSD
        License set forth in Section 4.c of the IETF Trust's Legal
        Provisions Relating to IETF Documents
        (http://trustee.ietf.org/license-info).
        This version of this YANG module is part of RFC XXXX; see
        the RFC itself for full legal notices.";

    revision 2017-06-16 {
        description
            "Added header fields for TCP, UDP, and ICMP.";
        reference
            "RFC XXX: Network Access Control List (ACL) YANG Data Model.";
    }

    revision 2016-10-12 {
        description
            "Initial version of packet fields used by
            ietf-access-control-list";
        reference
            "RFC XXXX: Network Access Control List (ACL)
            YANG Data  Model";
    }
    /* Draft version taken from: https://tools.ietf.org/html/draft-ietf-netmod-acl-model-11 */

    grouping acl-transport-header-fields {
        description
            "Transport header fields";
        container source-port-range {
            presence "Enables setting source port range";
            description
                "Inclusive range representing source ports to be used.
                When only lower-port is present, it represents a single port.";
            leaf lower-port {
                type inet:port-number;
                mandatory true;
                description
                    "Lower boundary for port.";
            }
            leaf upper-port {
                type inet:port-number;
                must ". >= ../lower-port" {
                    error-message
                        "The upper-port must be greater than or equal
                        to lower-port";
                }
                description
                    "Upper boundary for port . If existing, the upper port
                    must be greater or equal to lower-port.";
            }
        }

        container destination-port-range {
            presence "Enables setting destination port range";
            description
                "Inclusive range representing destination ports to be used.
                When only lower-port is present, it represents a single
                port.";

            leaf lower-port {
                type inet:port-number;
                mandatory true;
                description

                    "Lower boundary for port.";
            }
            leaf upper-port {
                type inet:port-number;
                must ". >= ../lower-port" {
                    error-message
                        "The upper-port must be greater than or equal
                        to lower-port";
                }

                description
                    "Upper boundary for port. If existing, the upper port must
                    be greater or equal to lower-port";
            }
        }
    }
    grouping acl-ip-header-fields {
        description
            "IP header fields common to ipv4 and ipv6";
        reference
            "RFC 791.";

        leaf tos {
            type uint8;
            description
                "Also known as Traffic Class in IPv6. The Type of Service (TOS)
                provides an indication of the abstract parameters of the
                quality of service desired.";
            reference
                "RFC 719, RFC 2460";
        }

        leaf length {
            type uint16;
            description
                "In IPv4 header field, this field is known as the Total Length.
                Total Length is the length of the datagram, measured in octets,
                      including internet header and data.

                          In IPv6 header field, this field is known as the Payload
                          Length, the length of the IPv6 payload, i.e. the rest of
                          the packet following the IPv6 header, in octets.";
            reference
                "RFC 719, RFC 2460";
        }

        leaf ttl {
            type uint8;
            description
                "This field indicates the maximum time the datagram is allowed
                to remain in the internet system.  If this field contains the
                value zero, then the datagram must be destroyed.

                In IPv6, this field is known as the Hop Limit.";
            reference "RFC 719, RFC 2460";
        }

        leaf protocol {
            type uint8;
            description
                "Internet Protocol number.";
        }
        uses acl-transport-header-fields;
    }
    grouping acl-ipv4-header-fields {
        description
            "Fields in IPv4 header.";

        leaf ihl {
            type uint8 {
                range "5..60";
            }
            description
                "An IPv4 header field, the Internet Header Length (IHL) is
                the length of the internet header in 32 bit words, and
                thus points to the beginning of the data. Note that the
                minimum value for a correct header is 5.";
        }

        leaf flags {
            type bits {
                bit reserved {
                    position 0;
                    description
                        "Reserved. Must be zero.";
                }
                bit fragment {
                    position 1;
                    description
                        "Setting value to 0 indicates may fragment, while setting
                        the value to 1 indicates do not fragment.";
                }
                bit more {
                    position 2;
                    description
                        "Setting the value to 0 indicates this is the last fragment,
                        and setting the value to 1 indicates more fragments are
                            coming.";
                }
            }
            description
                "Bit definitions for the flags field in IPv4 header.";
        }

        leaf offset {
            type uint16 {
                range "20..65535";
            }
            description
                "The fragment offset is measured in units of 8 octets (64 bits).
                The first fragment has offset zero. The length is 13 bits";
        }
        leaf identification {
            type uint16;
            description
                "An identifying value assigned by the sender to aid in
                assembling the fragments of a datagram.";
        }

        leaf destination-ipv4-network {
            type inet:ipv4-prefix;
            description
                "Destination IPv4 address prefix.";
        }
        leaf source-ipv4-network {
            type inet:ipv4-prefix;
            description
                "Source IPv4 address prefix.";
        }
    }

    grouping acl-ipv6-header-fields {
        description
            "Fields in IPv6 header";

        leaf next-header {
            type uint8;
            description
                "Identifies the type of header immediately following the
                IPv6 header. Uses the same values as the IPv4 Protocol
                field.";
            reference
                "RFC 2460";
        }

        leaf destination-ipv6-network {
            type inet:ipv6-prefix;
            description
                "Destination IPv6 address prefix.";
        }

        leaf source-ipv6-network {
            type inet:ipv6-prefix;
            description
                "Source IPv6 address prefix.";
        }

        leaf flow-label {
            type inet:ipv6-flow-label;
            description
                "IPv6 Flow label.";
        }
        reference
            "RFC 4291: IP Version 6 Addressing Architecture
            RFC 4007: IPv6 Scoped Address Architecture
            RFC 5952: A Recommendation for IPv6 Address Text
            Representation";
    }

    grouping acl-eth-header-fields {
        description
            "Fields in Ethernet header.";

        leaf destination-mac-address {
            type yang:mac-address;
            description
                "Destination IEEE 802 MAC address.";
        }
        leaf destination-mac-address-mask {
            type yang:mac-address;
            description
                "Destination IEEE 802 MAC address mask.";
        }
        leaf source-mac-address {
            type yang:mac-address;
            description
                "Source IEEE 802 MAC address.";
        }
        leaf source-mac-address-mask {
            type yang:mac-address;
            description
                "Source IEEE 802 MAC address mask.";
        }
        leaf ether-type {
            type string {
                pattern '[0-9a-fA-F]{4}';
            }
            description
                "The Ethernet Type (or Length) value represented
                in the canonical order defined by IEEE 802.
                The canonical representation uses lowercase
                characters.

                Note: This is not the most ideal way to define
                ether-types. Ether-types are well known types
                and are registered with RAC in IEEE. So they
                should well defined types with values. For now
                this model is defining it as a string.
                There is a note out to IEEE that needs to be
                turned into a liaison statement asking them to
                define all ether-types for the industry to use.";
            reference
                "IEEE 802-2014 Clause 9.2";
        }
        reference
            "IEEE 802: IEEE Standard for Local and Metropolitan
            Area Networks: Overview and Architecture.";
    }

    grouping acl-tcp-header-fields {
        description
            "Collection of TCP header fields that can be used to
            setup a match filter.";

        leaf sequence-number {
            type uint32;
            description
                "Sequence number that appears in the packet.";
        }

        leaf acknowledgement-number {
            type uint32;
            description
                "The acknowledgement number that appears in the
                packet.";
        }

        leaf data-offset {
            type uint8 {
                range "5..15";
            }
            description
                "Specifies the size of the TCP header in 32-bit
                words. The minimum size header is 5 words and
                the maximum is 15 words thus giving the minimum
                size of 20 bytes and maximum of 60 bytes,
                     allowing for up to 40 bytes of options in the
                         header.";
        }

        leaf reserved {
            type uint8;
            description
                "Reserved for future use.";
        }

        leaf flags {
            type uint16;
            description
                "Also known as Control Bits. Contains 9 1-bit flags.";
        }

        leaf window-size {
            type uint16;
            description
                "The size of the receive window, which specifies
                the number of window size units (by default,
                        bytes) (beyond the segment identified by the
                            sequence number in the acknowledgment field)
                            that the sender of this segment is currently
                            willing to receive.";
        }

        leaf urgent-pointer {
            type uint16;
            description
                "This field s an offset from the sequence number
                indicating the last urgent data byte.";
        }

        leaf options {
            type uint32;
            description
                "The length of this field is determined by the
                data offset field. Options have up to three
                fields: Option-Kind (1 byte), Option-Length
                (1 byte), Option-Data (variable). The Option-Kind
                field indicates the type of option, and is the
                only field that is not optional. Depending on
                what kind of option we are dealing with,
                     the next two fields may be set: the Option-Length
                         field indicates the total length of the option,
                     and the Option-Data field contains the value of
                         the option, if applicable.";
        }
    }

    grouping acl-udp-header-fields {
        description
            "Collection of UDP header fields that can be used
            to setup a match filter.";

        leaf length {
            type uint16;
            description
                "A field that specifies the length in bytes of
                the UDP header and UDP data. The minimum
                length is 8 bytes because that is the length of
                the header. The field size sets a theoretical
                limit of 65,535 bytes (8 byte header + 65,527
                        bytes of data) for a UDP datagram. However the
                actual limit for the data length, which is
                imposed by the underlying IPv4 protocol, is
                65,507 bytes (65,535 minus 8 byte UDP header
                        minus 20 byte IP header).

                In IPv6 jumbograms it is possible to have
                UDP packets of size greater than 65,535 bytes.
                RFC 2675 specifies that the length field is set
                to zero if the length of the UDP header plus
                UDP data is greater than 65,535.";
        }
    }

    grouping acl-icmp-header-fields {
        description
            "Collection of ICMP header fields that can be
            used to setup a match filter.";

        leaf type {
            type uint8;
            description
                "Also known as Control messages.";
            reference "RFC 792";
        }

        leaf code {
            type uint8;
            description
                "ICMP subtype. Also known as Control messages.";
        }

        leaf rest-of-header {
            type uint32;
            description
                "Four-bytes field, contents vary based on the
                ICMP type and code.";
        }
    }
}
